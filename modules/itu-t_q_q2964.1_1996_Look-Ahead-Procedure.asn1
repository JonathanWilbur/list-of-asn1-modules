Look-Ahead-Procedure (Q.2964.1:07/1996)


-- Module Look-Ahead-Procedure (Q.2964.1:07/1996)
-- See also ITU-T Q.2964.1 (07/1996)
-- See also the index of all ASN.1 assignments needed in this document

Look-Ahead-Procedure {itu-t recommendation q 2964 operations-and-errors(1)}
DEFINITIONS EXPLICIT TAGS ::=
BEGIN

EXPORTS lookAhead, lookAheadTb;

IMPORTS
  OPERATION, ERROR
    FROM Remote-Operations-Information-Objects {joint-iso-itu-t
      remote-operations(4) informationObjects(5) version1(0)}
  DSS2InformationElement
    FROM Embedded-DSS2Types {itu-t recommendation q 2932 embedded-dSS2-types(7)
      }
  Address
    FROM Addressing-Data-Elements {itu-t recommendation q 932
      addressing-data-elements(7)}
  CauseIndicators
    FROM LookAheadParameters {itu-t recommendation q 2724 1 modules(0)
      parameters(2) version1(0)}
  systemFailure, taskRefused
    FROM IN-CS-1-Errors {itu-t(0) recommendation(0) q(17) 1218 modules(0)
      cs-1-errors(1) version1(0)};

lookAhead OPERATION ::= {
  ARGUMENT  DSS2InformationElement
  -- The following information elements
  -- shall be embedded in DSS2InformationElement:
  -- AAL parameters		optional
  -- ATM traffic descriptor
  -- Broadband bearer capability
  -- Broadband high layer information		optional
  -- Broadband low layer information		optional
  -- OAM traffic descriptor		optional
  -- QOS parameter
  -- Narrow-band bearer capability		optional
  -- Narrow-band high layer compatibility		optional
  -- Narrow-band low layer compatibility		optional
  -- The B-LLI, N-BC and N-LLI information elements may be repeated
  RESULT    LookResult
  CODE      local:501
}

--LookAhead		LookAhead		::= localValue 501
LookResult ::= ENUMERATED {
  compatibleAndFree(0), compatibleAndBusy(1), incompatible(2)}

lookAheadTb OPERATION ::= {
  ARGUMENT
    SET {address                 Address,
         dSS2InformationElement  DSS2InformationElement
         -- The following information elements
         -- shall be embedded in DSS2InfoElement:
         -- AAL parameters				optional
         -- ATM traffic descriptor
         -- Broadband bearer capability
         -- Broadband high layer information		optional
         -- Broadband low layer information		optional
         -- OAM traffic descriptor			optional
         -- QOS parameter
         -- Narrow-band bearer capability		optional
         -- Narrow-band high layer compatibility		optional
         -- Narrow-band low layer compatibility		optional
         -- The B-LLI, N-BC and N-LLI information elements may be repeated
  }
  RESULT    SET {lookResult       LookResult,
                 causeIndicators  CauseIndicators}
  ERRORS    {systemFailure | taskRefused}
  CODE      local:502
}

--LookAheadTb	LookAheadTb	::= localValue 502
END

-- Generated by Asnp, the ASN.1 pretty-printer of France Telecom R&D

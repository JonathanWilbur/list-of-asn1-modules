Text-Units (T.415:03/1993)


-- Module Text-Units (T.415:03/1993)
-- See also ITU-T T.415 (03/1993)
-- See also the index of all ASN.1 assignments needed in this document

Text-Units {2 8 1 5 12} DEFINITIONS ::=
BEGIN

EXPORTS Text-Unit, Type-Of-Coding;

IMPORTS
  Content-Portion-Identifier
    FROM Identifiers-and-Expressions --  see 7.8
      
  Character-Coding-Attributes
    FROM Character-Coding-Attributes {2 8 1 6 3
      } --  see ITU-T Rec. T.416 | ISO/IEC 8613-6
  Raster-Gr-Coding-Attributes
    FROM Raster-Gr-Coding-Attributes {2 8 1 7 3
      } --  see ITU-T Rec. T.417 | ISO/IEC 8613-7
  Geo-Gr-Coding-Attributes
    FROM Geo-Gr-Coding-Attributes {2 8 1 8 3
      } --  see ITU-T Rec. T.418 | ISO/IEC 8613-8
  Videotex-Coding-Attributes
    FROM Videotex-Coding-Attributes;

Text-Unit ::= SEQUENCE {
  content-portion-attributes  Content-Portion-Attributes OPTIONAL,
  content-information         Content-Information OPTIONAL
}

Content-Portion-Attributes ::= SET {
  content-identifier-layout   Content-Portion-Identifier OPTIONAL,
  content-identifier-logical  [4] IMPLICIT Content-Portion-Identifier OPTIONAL,
  type-of-coding              Type-Of-Coding OPTIONAL,
  coding-attributes
    CHOICE {character-coding-attributes
              [1] IMPLICIT Character-Coding-Attributes,
            raster-gr-coding-attributes
              [2] IMPLICIT Raster-Gr-Coding-Attributes,
            geo-gr-coding-attributes
              [7] IMPLICIT Geo-Gr-Coding-Attributes,
            videotex-coding-attributes
              [8] IMPLICIT Videotex-Coding-Attributes,
            --  the use of the data item "videotex-coding-attributes" is applicable to
            --  ITU-T Rec. T.410 Series only
            --  the following tags are reserved for additional types
            --  of coding attributes:
            --  [9] audio
            --  [10] dynamic-graphics
            ext-cont-arch-coding-attributes  [11] IMPLICIT EXTERNAL} OPTIONAL,
  alternative-representation  [3] IMPLICIT Alternative-Representation OPTIONAL
}

Content-Information ::= CHOICE {
  content        OCTET STRING,
  tiled-content  Tiled-Content
}

Tiled-Content ::= SEQUENCE OF OCTET STRING

Type-Of-Coding ::= CHOICE {
  a  [0] IMPLICIT INTEGER {t6(1)},
  b  [6] IMPLICIT OBJECT IDENTIFIER
}

Alternative-Representation ::= OCTET STRING

--  string of characters from the sets designated by the document
--  profile attribute "alternative representation character sets",
--  plus carriage return and line feed
END

-- Generated by Asnp, the ASN.1 pretty-printer of France Telecom R&D

MHSRoutingObjectIdentifiers (X.412:06/1999)


-- Module MHSRoutingObjectIdentifiers (X.412:06/1999)
-- See also ITU-T X.412 (06/1999)
-- See also the index of all ASN.1 assignments needed in this document

MHSRoutingObjectIdentifiers {joint-iso-itu-t mhs(6) routing(10) modules(0)
  object-identifiers(0)} DEFINITIONS ::=
BEGIN

-- Prologue
-- Exports everything
IMPORTS -- nothing -- ;

ID ::= OBJECT IDENTIFIER

-- MHS-routing
id-mhs-routing ID ::=
  {joint-iso-itu-t mhs(6) routing(10)} -- not definitive

-- Categories
id-mod ID ::= {id-mhs-routing  0} -- modules; not definitive

id-oc ID ::= {id-mhs-routing  1} -- object-classes

id-nf ID ::= {id-mhs-routing  2} -- name-forms

id-at ID ::= {id-mhs-routing  3} -- attributes

id-pro ID ::= {id-mhs-routing  4} -- profiles

id-wf ID ::= {id-mhs-routing  5} -- weighting factors

-- Modules
id-mod-object-identifiers ID ::= {id-mod  0} -- not definitive

id-mod-directory-objects ID ::= {id-mod  1} -- not definitive

id-mod-oraddress-subtree ID ::= {id-mod  2} -- not definitive

-- Object classes
id-oc-connection-group ID ::= {id-oc  0}

id-oc-mhs-admd ID ::= {id-oc  1}

id-oc-mhs-common-name ID ::= {id-oc  2}

id-oc-mhs-country ID ::= {id-oc  3}

id-oc-mhs-extended-network-address ID ::= {id-oc  4}

id-oc-mhs-generation-qualifier ID ::= {id-oc  5}

id-oc-mhs-given-name ID ::= {id-oc  6}

id-oc-mhs-initials ID ::= {id-oc  7}

id-oc-mhs-network-address ID ::= {id-oc  8}

id-oc-mhs-numeric-user-identifier ID ::= {id-oc  9}

id-oc-mhs-or-address-element ID ::= {id-oc  10}

id-oc-mhs-organization ID ::= {id-oc  11}

id-oc-mhs-organizational-unit ID ::= {id-oc  12}

id-oc-mhs-pds-name ID ::= {id-oc  13}

id-oc-mhs-physical-delivery-country-name ID ::= {id-oc  14}

id-oc-mhs-postal-code ID ::= {id-oc  15}

id-oc-mhs-prmd ID ::= {id-oc  16}

id-oc-mhs-surname ID ::= {id-oc  17}

id-oc-mhs-terminal-identifier ID ::= {id-oc  18}

id-oc-mhs-terminal-type ID ::= {id-oc  19}

id-oc-mta-information ID ::= {id-oc  20}

id-oc-oraddress-subtree-base ID ::= {id-oc  21}

id-oc-routing-collective ID ::= {id-oc  22}

id-oc-routing-mta ID ::= {id-oc  23}

-- Name forms
id-nf-connection-group ID ::= {id-nf  0}

id-nf-mhs-admd ID ::= {id-nf  1}

id-nf-mhs-common-name ID ::= {id-nf  2}

id-nf-mhs-country ID ::= {id-nf  3}

id-nf-mhs-extended-network-address ID ::= {id-nf  4}

id-nf-mhs-generation-qualifier ID ::= {id-nf  5}

id-nf-mhs-given-name ID ::= {id-nf  6}

id-nf-mhs-initials ID ::= {id-nf  7}

id-nf-mhs-network-address ID ::= {id-nf  8}

id-nf-mhs-numeric-user-identifier ID ::= {id-nf  9}

id-nf-mhs-organization ID ::= {id-nf  10}

id-nf-mhs-organizational-unit ID ::= {id-nf  11}

id-nf-mhs-pds-name ID ::= {id-nf  12}

id-nf-mhs-physical-delivery-country ID ::= {id-nf  13}

id-nf-mhs-postal-code ID ::= {id-nf  14}

id-nf-mhs-prmd ID ::= {id-nf  15}

id-nf-mhs-surname ID ::= {id-nf  16}

id-nf-mhs-terminal-identifier ID ::= {id-nf  17}

id-nf-mhs-terminal-type ID ::= {id-nf  18}

id-nf-routing-collective ID ::= {id-nf  19}

-- Attributes
id-at-calling-psaps ID ::= {id-at  0}

id-at-connection-group-name ID ::= {id-at  1}

id-at-connection-type ID ::= {id-at  2}

id-at-entry-connection-group-name ID ::= {id-at  3}

id-at-enumerated-flag ID ::= {id-at  4}

id-at-global-domain-identifier ID ::= {id-at  5}

id-at-group-mta-password ID ::= {id-at  6}

id-at-local-exit-connection-group-name ID ::= {id-at  7}

id-at-member-mta ID ::= {id-at  8}

id-at-mhs-admd-name ID ::= {id-at  9}

id-at-mhs-common-name ID ::= {id-at  10}

id-at-mhs-country-name ID ::= {id-at  11}

id-at-mhs-expression-matches ID ::= {id-at  12}

id-at-mhs-extended-network-address ID ::= {id-at  13}

id-at-mhs-generation-qualifier ID ::= {id-at  14}

id-at-mhs-given-name ID ::= {id-at  15}

id-at-mhs-initials ID ::= {id-at  16}

id-at-mhs-message-transfer-agent ID ::= {id-at  17}

id-at-mhs-network-address ID ::= {id-at  18}

id-at-mhs-next-level-complete ID ::= {id-at  19}

id-at-mhs-numeric-user-identifier ID ::= {id-at  20}

id-at-mhs-organization-name ID ::= {id-at  21}

id-at-mhs-organizational-unit-name ID ::= {id-at  22}

id-at-mhs-pds-name-attribute ID ::= {id-at  23}

id-at-mhs-postal-code ID ::= {id-at  24}

id-at-mhs-prmd-name ID ::= {id-at  25}

id-at-mhs-routing-advice ID ::= {id-at  26}

id-at-mhs-surname ID ::= {id-at  27}

id-at-mhs-terminal-identifier ID ::= {id-at  28}

id-at-mhs-terminal-type ID ::= {id-at  29}

id-at-mta-name ID ::= {id-at  30}

id-at-mta-password ID ::= {id-at  31}

id-at-oraddress-element-name ID ::= {id-at  32}

id-at-oraddress-subtrees ID ::= {id-at  33}

id-at-recipient-md-assigned-alternate-recipient ID ::= {id-at  34}

id-at-routing-collective-name ID ::= {id-at  35}

id-at-security-context ID ::= {id-at  36}

id-at-specific-passwords ID ::= {id-at  37}

id-at-transit-exit-connection-group-name ID ::= {id-at  38}

-- Profiles
id-pro-x25 ID ::= {id-pro  0}

id-pro-rfc1006 ID ::= {id-pro  1}

id-pro-x445 ID ::= {id-pro  2}

-- Weighting factors
id-wf-integer ID ::= {id-wf  0} -- integer weighting factor

END -- of MHS-Routing Object Identifiers 

-- Generated by Asnp, the ASN.1 pretty-printer of France Telecom R&D

XYZ (X.694 (2004) Amd.1:05/2007)


-- Module XYZ (X.694 (2004) Amd.1:05/2007)
-- See also ITU-T X.694 (2004) Amend. 1 (05/2007)
-- See also the index of all ASN.1 assignments needed in this document

XYZ -- The module reference is not standardized
DEFINITIONS XER INSTRUCTIONS AUTOMATIC TAGS ::=
BEGIN

IMPORTS
  String
    FROM XSD {joint-iso-itu-t asn1(1) specification(0) modules(0) xsd-module(2)
      version1(1)};

/* For a Version 2 mapping, the last component of the module
                    identifier would be version2(2) */
Xyz-elem ::= [NAME AS UNCAPITALIZED] XSD.String

Xyz-type ::= SEQUENCE {xyz-attr [ATTRIBUTE] BOOLEAN OPTIONAL}

ENCODING-CONTROL XER
	GLOBAL-DEFAULTS MODIFIED-ENCODINGS
	GLOBAL-DEFAULTS CONTROL-NAMESPACE
		"http://www.w3.org/2001/XMLSchema-instance"
		NAMESPACE ALL AS "http://example.com/xyz"
END

-- Generated by Asnp, the ASN.1 pretty-printer of France Telecom R&amp;D

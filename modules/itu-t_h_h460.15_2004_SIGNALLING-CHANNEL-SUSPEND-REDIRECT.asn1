SIGNALLING-CHANNEL-SUSPEND-REDIRECT (H.460.15:03/2004)


-- Module SIGNALLING-CHANNEL-SUSPEND-REDIRECT (H.460.15:03/2004)
-- See also ITU-T H.460.15 (03/2004)
-- See also the index of all ASN.1 assignments needed in this document

SIGNALLING-CHANNEL-SUSPEND-REDIRECT DEFINITIONS AUTOMATIC TAGS ::=
BEGIN

IMPORTS TransportAddress
          FROM H323-MESSAGES;

SignallingChannelData ::= SEQUENCE {
  signallingChannelData
    CHOICE {channelSuspendRequest   ChannelSuspendRequest,
            channelSuspendResponse  ChannelSuspendResponse,
            channelSuspendConfirm   ChannelSuspendConfirm,
            channelSuspendCancel    ChannelSuspendCancel,
            channelResumeRequest    ChannelResumeRequest,
            channelResumeResponse   ChannelResumeResponse,
            ...},
  ...
}

ChannelSuspendRequest ::= SEQUENCE {
  channelResumeAddress  SEQUENCE OF TransportAddress,
  immediateResume       BOOLEAN,
  resetH245             NULL OPTIONAL,
  ...
}

ChannelSuspendResponse ::= SEQUENCE {
  okToSuspend           BOOLEAN,
  channelResumeAddress  SEQUENCE OF TransportAddress,
  ...
}

ChannelSuspendConfirm ::= SEQUENCE {...
}

ChannelSuspendCancel ::= SEQUENCE {...
}

ChannelResumeRequest ::= SEQUENCE {
  randomNumber  INTEGER(0..4294967295),
  resetH245     NULL OPTIONAL,
  ...
}

ChannelResumeResponse ::= SEQUENCE {...
}

END -- of ASN.1

-- Generated by Asnp, the ASN.1 pretty-printer of France Telecom R&D

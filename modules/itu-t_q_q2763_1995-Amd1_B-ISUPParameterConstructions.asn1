B-ISUPParameterConstructions (Q.2763:12/1999)


-- Module B-ISUPParameterConstructions (Q.2763:12/1999)
-- See also ITU-T Q.2763 (1999) Amend. 1 (12/2002)
-- See also the index of all ASN.1 assignments needed in this document

B-ISUPParameterConstructions DEFINITIONS IMPLICIT TAGS ::=
BEGIN

IMPORTS
  AALParametersField, AddressSignal, BinaryCode,
    BroadbandBearerCapabilityField, BroadbandHighLayerInformationField,
    BroadbandLowLayerInformationField, CalledAddressSignal,
    CalledPartySubaddressField, CallingAddressSignal,
    CallingPartySubaddressField, CellRateID, ConnectedSubaddressField,
    ControlID, DelayValue, MLPPServiceDomain, NarrowbandBearerCapabilityField,
    NarrowbandHighLayerCompaField, NarrowbandLowLayerCompaField, NIdigit,
    OAMTrafficDescriptorField, ProgressIndicatorField, RedirectionCounter,
    SignallingPointCode, UserToUserInformationField, VirtualChannelID,
    VirtualPathConnectionID
    FROM B-ISUPParameterElements
  AccessDeliveryIndicator, AddressPresentationIndicator,
    AutomaticCongestionLevelInd, CallDiversionMayOccurIndicator,
    CalledPartysCategoryInd, CalledPartysStatusInd,
    CallingPartysCategoryIndicators, CCITTNetworkIdenPlanIndicator,
    CellRateIdentifier, ChargeIndicator, ClosedUserGroupCallIndicator,
    ConnectedLineIDRequestIndicator, InBandInformationIndicator,
    IncomingHECDIndicator, IncomingHECDRequestIndicator,
    InternalNetworkNumberIndicator, InterworkingIndicator, ISDNAccessIndicator,
    ISDNUserPartIndicator, ISDNUserPartPreferenceInd,
    LookAheadForBusyIndicator, MLPPUserIndicator, MoreDataIndicator,
    NationalNetworkIdenPlanIndicator, NationalInternationalCallIndicator,
    NatureOfAddressIndicator, NetworkDiscardIndicator, NotificationIndicators,
    NotificationSubscriptionOption, NumberIncompleteIndicator,
    NumberingPlanIndicator, OriginalRedirectionReasonIndicator,
    OutgoingHECDIndicator, OutgoingHECDRequestIndicator,
    PrecedenceLevelIndicator, Priority, RedirectingIndicator,
    RedirectingReasonIndicator, RedirectionNumberRestrictionInd,
    RepeatIndicator, ResourceIndicator, ScreeningIndicator,
    SimpleSegmentationIndicator, SuspendResumeIndicator, Type,
    TypeOfNetworkIdentification, UserToUserServiceRequest,
    UserToUserServiceResponse, VPCICheckResultIndicator
    FROM B-ISUPParameterIndicators;

ATMCellRateField ::= SEQUENCE {
  cellRateIdentifier  CellRateIdentifier,
  cellRateID          CellRateID
}

CalledPartyAddress ::= SEQUENCE SIZE (0..16) OF CalledAddressSignal

CallingPartyAddress ::= SEQUENCE SIZE (0..16) OF CallingAddressSignal

ClosedUserGroupInterlockCode ::= SEQUENCE {
  networkIdentity  NetworkIdentity,
  binaryCode       BinaryCode
}

ConnectedAddress ::= SEQUENCE SIZE (0..16) OF CallingAddressSignal

ConnectionElementID ::= SEQUENCE {
  virtualPathConnectionID  VirtualPathConnectionID,
  virtualChannelID         [1]  VirtualChannelID OPTIONAL
}

LocationAddress ::= SEQUENCE SIZE (0..16) OF AddressSignal

NetworkIdentification ::= SEQUENCE SIZE (0..16) OF CalledAddressSignal

NetworkIdentificationPlan ::= CHOICE {
  cCITTNetworkIdenPlanIndicator     CCITTNetworkIdenPlanIndicator,
  nationalNetworkIdenPlanIndicator  NationalNetworkIdenPlanIndicator
}

NetworkIdentity ::= SEQUENCE SIZE (4) OF NIdigit

ResourceValue ::= CHOICE {
  controlID                ControlID,
  connectionElementID      ConnectionElementID,
  virtualPathConnectionID  VirtualPathConnectionID
}

SubsequentAddress ::= SEQUENCE SIZE (0..16) OF CalledAddressSignal

UserToUserIndicatorsParameter ::= CHOICE {
  userToUserRequest   [0]  UserToUserRequest,
  userToUserResponse  [1]  UserToUserResponse
}

UserToUserRequest ::= SEQUENCE {
  service1  UserToUserServiceRequest,
  service2  UserToUserServiceRequest,
  service3  UserToUserServiceRequest
}

UserToUserResponse ::= SEQUENCE {
  service1                           UserToUserServiceResponse,
  service2                           UserToUserServiceResponse,
  service3                           UserToUserServiceResponse,
  userToUserNetworkDiscardIndicator  NetworkDiscardIndicator
}

END

-- Generated by Asnp, the ASN.1 pretty-printer of France Telecom R&D

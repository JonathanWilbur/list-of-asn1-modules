MHSObjectIdentifiers (X.402:06/1999)


-- Module MHSObjectIdentifiers (X.402:06/1999)
-- See also ITU-T X.402 (06/1999)
-- See also the index of all ASN.1 assignments needed in this document

MHSObjectIdentifiers {joint-iso-itu-t mhs(6) arch(5) modules(0)
  object-identifiers(0) version-1999(1)} DEFINITIONS IMPLICIT TAGS ::=
BEGIN

-- Prologue
-- Exports everything.
IMPORTS -- nothing -- ;

ID ::= OBJECT IDENTIFIER

-- MHS Aspects
id-mhs-protocols ID ::= {joint-iso-itu-t mhs(6) protocols(0)}

-- MHS Application Contexts and Protocols
-- See ITU-T Rec. X.419 | ISO/IEC 10021-6.
id-ipms ID ::=
  {joint-iso-itu-t mhs(6) ipms(1)}

-- Interpersonal Messaging
-- See ITU-T Rec. X.420 | ISO/IEC 10021-7.
--  Value {joint-iso-itu-t mhs(6) 2} is no longer defined
id-mts ID ::=
  {joint-iso-itu-t mhs(6) mts(3)}

-- Message Transfer System
-- See ITU-T Rec. X.411 | ISO/IEC 10021-4.
id-ms ID ::=
  {joint-iso-itu-t mhs(6) ms(4)}

-- Message Store
-- See ITU-T Rec. X.413 | ISO/IEC 10021-5.
id-arch ID ::=
  {joint-iso-itu-t mhs(6) arch(5)}

-- Overall Architecture
-- See this Specification.
id-group ID ::=
  {joint-iso-itu-t mhs(6) group(6)}

-- Reserved.
id-edims ID ::= {joint-iso-itu-t mhs(6) edims(7)}

-- EDI Messaging
-- See ITU-T Rec. X.435 | ISO/IEC 10021-9.
id-management ID ::=
  {joint-iso-itu-t mhs(6) management(9)}

-- MHS Management
-- See ITU-T Recs. X.460 - X.467 | ISO/IEC 11588.
id-routing ID ::=
  {joint-iso-itu-t mhs(6) routing(10)}

-- MHS Routing
-- See ITU-T Rec. X.412 | ISO/IEC 10021-10.
-- Categories
id-mod ID ::=
  {id-arch  0} -- modules; not definitive

id-oc ID ::= {id-arch  1} -- object classes

id-at ID ::= {id-arch  2} -- attribute types

--  Value {id-arch  3} is no longer defined
id-mr ID ::=
  {id-arch  4} -- matching rules

id-con ID ::= {id-arch  5} -- contexts

id-san ID ::= {id-arch  6} -- certificate subject alternative names

-- Modules
id-object-identifiers ID ::= {id-mod  0} -- not definitive

id-directory-objects-and-attributes ID ::= {id-mod  1} -- not definitive

-- Object classes
id-oc-mhs-distribution-list ID ::= {id-oc  0}

id-oc-mhs-message-store ID ::= {id-oc  1}

id-oc-mhs-message-transfer-agent ID ::= {id-oc  2}

id-oc-mhs-user ID ::= {id-oc  3}

id-oc-mhs-user-agent ID ::= {id-oc  4}

-- Attributes
id-at-mhs-maximum-content-length ID ::= {id-at  0}

id-at-mhs-deliverable-content-types ID ::= {id-at  1}

id-at-mhs-exclusively-acceptable-eits ID ::= {id-at  2}

id-at-mhs-dl-members ID ::= {id-at  3}

id-at-mhs-dl-submit-permissions ID ::= {id-at  4}

id-at-mhs-message-store-dn ID ::= {id-at  5}

id-at-mhs-or-addresses ID ::= {id-at  6}

--  Value {id-at  7} is no longer defined
id-at-mhs-supported-automatic-actions ID ::=
  {id-at  8}

id-at-mhs-supported-content-types ID ::= {id-at  9}

id-at-mhs-supported-attributes ID ::= {id-at  10}

id-at-mhs-supported-matching-rules ID ::= {id-at  11}

id-at-mhs-dl-archive-service ID ::= {id-at  12}

id-at-mhs-dl-policy ID ::= {id-at  13}

id-at-mhs-dl-related-lists ID ::= {id-at  14}

id-at-mhs-dl-subscription-service ID ::= {id-at  15}

id-at-mhs-or-addresses-with-capabilities ID ::= {id-at  16}

id-at-mhs-acceptable-eits ID ::= {id-at  17}

id-at-mhs-unacceptable-eits ID ::= {id-at  18}

id-at-mhs-deliverable-classes ID ::= {id-at  19}

id-at-encrypted-mhs-maximum-content-length ID ::= {id-at 0 2}

id-at-encrypted-mhs-deliverable-content-types ID ::= {id-at 1 2}

id-at-encrypted-mhs-exclusively-acceptable-eits ID ::= {id-at 2 2}

id-at-encrypted-mhs-dl-members ID ::= {id-at 3 2}

id-at-encrypted-mhs-dl-submit-permissions ID ::= {id-at 4 2}

id-at-encrypted-mhs-message-store-dn ID ::= {id-at 5 2}

id-at-encrypted-mhs-or-addresses ID ::= {id-at 6 2}

id-at-encrypted-mhs-supported-automatic-actions ID ::= {id-at 8 2}

id-at-encrypted-mhs-supported-content-types ID ::= {id-at 9 2}

id-at-encrypted-mhs-supported-attributes ID ::= {id-at 10 2}

id-at-encrypted-mhs-supported-matching-rules ID ::= {id-at 11 2}

id-at-encrypted-mhs-dl-archive-service ID ::= {id-at 12 2}

id-at-encrypted-mhs-dl-policy ID ::= {id-at 13 2}

id-at-encrypted-mhs-dl-related-lists ID ::= {id-at 14 2}

id-at-encrypted-mhs-dl-subscription-service ID ::= {id-at 15 2}

id-at-encrypted-mhs-or-addresses-with-capabilities ID ::= {id-at 16 2}

id-at-encrypted-mhs-acceptable-eits ID ::= {id-at 17 2}

id-at-encrypted-mhs-unacceptable-eits ID ::= {id-at 18 2}

id-at-encrypted-mhs-deliverable-classes ID ::= {id-at 19 2}

-- Matching Rules
id-mr-orname-exact-match ID ::= {id-mr  0}

id-mr-address-capabilities-match ID ::= {id-mr  1}

id-mr-capability-match ID ::= {id-mr  2}

-- Contexts
id-con-dl-administrator-annotation ID ::= {id-con  0}

id-con-dl-nested-dl ID ::= {id-con  1}

id-con-dl-reset-originator ID ::= {id-con  2}

-- Certificate subject alternative names
id-san-mta-name ID ::= {id-san  0}

END -- of MHSObjectIdentifiers

-- Generated by Asnp, the ASN.1 pretty-printer of France Telecom R&D

CCNR-Protocol (Q.733.5:12/1999)


-- Module CCNR-Protocol (Q.733.5:12/1999)
-- See also ITU-T Q.733.5 (12/1999)
-- See also the index of all ASN.1 assignments needed in this document

CCNR-Protocol {itu-t recommendation q 733 5 modules(2) operations-and-errors(1)
  version1(1)} DEFINITIONS EXPLICIT TAGS ::=
BEGIN

IMPORTS
  OPERATION, ERROR
    FROM Remote-Operations-Information-Objects {joint-iso-itu-t
      remote-operations(4) informationObjects(5) version1(0)}
  ccbsCancel, ccbsSuspend, ccbsResume, remoteUserFree, shortTermDenial,
    longTermDenial, CauseCode, USICode, AccessTransport,
    maxAccessTransportLength
    FROM CCBS-Protocol {itu-t recommendation q 733 3 modules(2)
      operations-and-errors(1) version1(1)};

-- operations types
ccnrRequest OPERATION ::= {
  ARGUMENT
    SEQUENCE {calledPartyNumber         CalledPartyNumber,
              retainSupported           BOOLEAN DEFAULT FALSE,
              userServiceInf            [1] IMPLICIT USICode OPTIONAL,
              callingPartyNumber
                [2] IMPLICIT CallingPartyNumber OPTIONAL,
              userServiceInfPrime       [3] IMPLICIT USICode OPTIONAL,
              accessTransportParameter  [4] IMPLICIT AccessTransport OPTIONAL,
              additionalCalledNumber    [5] IMPLICIT GenericNumber OPTIONAL,
              ...}
  RESULT    SEQUENCE {retainSupported  BOOLEAN DEFAULT FALSE,
                      ...}
  ERRORS    {shortTermDenial | longTermDenial}
  CODE      global:{ccnrOID ccnrrequest(1)}
}

-- constants and data type definitions
CalledPartyNumber ::= OCTET STRING(SIZE (3..maxCalledPartyNumberLength))

-- the called party number is coded as described in
-- Recommendation Q.763 [10], Called Party Number parameter.
CallingPartyNumber ::= OCTET STRING(SIZE (3..maxCallingPartyNumberLength))

-- the calling party number is coded as described in
-- Recommendation Q.763 [10], Calling Party Number parameter.
GenericNumber ::= OCTET STRING(SIZE (3..maxGenericNumberLength))

-- numbers of the GenericNumber type are coded as described in
-- Recommendation Q.763 [10], Generic Number parameter,
-- without the Number Qualifier indicator.
maxCalledPartyNumberLength INTEGER ::=
  255

maxCallingPartyNumberLength INTEGER ::= 255

maxGenericNumberLength INTEGER ::= 255

-- object identifier path
ccnrOID OBJECT IDENTIFIER ::=
  {itu-t recommendation q 733 5 operations-and-errors(1)}

END -- of CCNR-Protocol

-- Generated by Asnp, the ASN.1 pretty-printer of France Telecom R&D

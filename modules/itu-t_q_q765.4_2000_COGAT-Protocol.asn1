COGAT-Protocol (Q.765.4:06/2000)


-- Module COGAT-Protocol (Q.765.4:06/2000)
-- See also ITU-T Q.765.4 (06/2000)
-- See also the index of all ASN.1 assignments needed in this document

COGAT-Protocol {itu-t(0) recommendation(0) q(17) q765(765) q765-4(4) 
  modules(2) operations-and-errors(1) version1(1)} DEFINITIONS IMPLICIT TAGS ::=
BEGIN

IMPORTS
  OPERATION, ERROR
    FROM Remote-Operations-Information-Objects {joint-iso-itu-t
      remote-operations(4) informationObjects(5) version1(0)}
  GATPDU{}
    FROM GAT-PDU {itu-t recommendation q 860 gat-pdu(1)};

-- TYPE DEFINITIONS FOR OPERATIONS
--Specification of Setup
-- =================
--Direction:	OLEX ® DLEX
--Class:	3
--Timer:	T1
--Purpose:	Used for the establishment of a signalling association between a PIN and a PAN for a bearer unrelated signalling connection.
setUp{OPERATION:Invokable, OPERATION:Returnable} OPERATION ::= {
  ARGUMENT  SetUpArg {{Invokable},
                      {Returnable}}
  RESULT    SetUpResultArg {{Invokable},
                            {Returnable}}
  CODE      global:{cOGATOID setUp(1)}
}

--Specification of Release
-- ==================
--Direction:	OLEX ® DLEX and DLEX ® OLEX
--Class:	4
--Purpose:	Used for releasing a signalling association between a PIN and a PAN.
release{OPERATION:Invokable, OPERATION:Returnable} OPERATION ::= {
  ARGUMENT  ReleaseArg {{Invokable},
                        {Returnable}}
  CODE      global:{cOGATOID release(2)}
}

--Specification of GATData
-- ====================
--Direction:	OLEX ® DLEX and DLEX ® OLEX
--Class:	4
--Purpose:	Used for transporting GAT information flows during the active phase of a signalling connection.
gATData{OPERATION:Invokable, OPERATION:Returnable} OPERATION ::= {
  ARGUMENT  GATDataArg {{Invokable},
                        {Returnable}}
  CODE      global:{cOGATOID gatData(3)}
}

--Specification of ActivityTest
-- =====================
--Direction:	OLEX ® DLEX
--Class:	3
--Timer:	T2
--Purpose:	Used to determine if the signalling association remains established between a PIN and a PAN.
activityTest OPERATION ::= {CODE  global:{cOGATOID activityTest(4)}
}

--TYPE DEFINITIONS FOR ERRORS
-- TYPE DEFINITIONS FOR ARGUMENT DATA
SetUpArg{OPERATION:Invokable, OPERATION:Returnable} ::= SEQUENCE {
  destinationAddress  CalledPartyNumber,
  gATPDU              GATPDU{{Invokable}, {Returnable}},
  ...
}

SetUpResultArg{OPERATION:Invokable, OPERATION:Returnable} ::= SEQUENCE {
  cause   Cause,
  gATPDU  GATPDU{{Invokable}, {Returnable}},
  ...
}

ReleaseArg{OPERATION:Invokable, OPERATION:Returnable} ::= SEQUENCE {
  cause   Cause,
  gATPDU  GATPDU{{Invokable}, {Returnable}},
  ...
}

GATDataArg{OPERATION:Invokable, OPERATION:Returnable} ::=
  GATPDU{{Invokable}, {Returnable}}

--TYPE DEFINITIONS FOR DATA
CalledPartyNumber ::= OCTET STRING(SIZE (1..maxcdPlength))

--The CalledPartyNumber is coded as described in Recommendation Q.763 [3].
--The ISUP parameter name and length octets are not included.
Cause ::= OCTET STRING(SIZE (1..maxCauseLength))

--The Cause is coded as described in Recommendation Q.850 [18].
--The information element identifier and length octets are not included.
--DEFINITION OF RANGE CONSTANTS
maxCauseLength INTEGER ::=
  30

maxLength INTEGER ::= 2048

maxcdPlength INTEGER ::= 1 -- Network specific

--DEFINITION OF OBJECT IDENTIFIER PATH
cOGATOID OBJECT IDENTIFIER ::=
  {itu-t(0) recommendation(0) q(17) q765(765) q765-4(4) modules(2)
   operations-and-errors(1)} --of COGAT-Protocol

END

-- Generated by Asnp, the ASN.1 pretty-printer of France Telecom R&D

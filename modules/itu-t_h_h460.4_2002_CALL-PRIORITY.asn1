CALL-PRIORITY (H.460.4:11/2002)


-- Module CALL-PRIORITY (H.460.4:11/2002)
-- See also ITU-T H.460.4 (11/2002)
-- See also the index of all ASN.1 assignments needed in this document

CALL-PRIORITY {itu-t(0) recommendation(0) h(8) 460 4 version(0)} DEFINITIONS
AUTOMATIC TAGS ::=
BEGIN

IMPORTS ClearToken, CryptoToken
          FROM H235-SECURITY-MESSAGES;

CallPriorityInfo ::= SEQUENCE -- root for Call Priority related asn.1
                      {
  priorityValue
    CHOICE {emergencyAuthorized  NULL,
            emergencyPublic      NULL,
            high                 NULL,
            normal               NULL,
            ...},
  priorityExtension  INTEGER(0..255) OPTIONAL,
  tokens             SEQUENCE OF ClearToken OPTIONAL,
  cryptoTokens       SEQUENCE OF CryptoToken OPTIONAL,
  rejectReason
    CHOICE {priorityUnavailable   NULL,
            priorityUnauthorized  NULL,
            priorityValueUnknown  NULL,
            ...} OPTIONAL, -- Only used in CallPriorityConfirm
  ...
}

END -- of ASN.1

-- Generated by Asnp, the ASN.1 pretty-printer of France Telecom R&D

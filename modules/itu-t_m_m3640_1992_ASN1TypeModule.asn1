ASN1TypeModule (M.3640:10/1992)


-- Module ASN1TypeModule (M.3640:10/1992)
-- See also ITU-T M.3640 (10/1992)
-- See also the index of all ASN.1 assignments needed in this document

ASN1TypeModule {itu-t(0) recommendation(0) m(13) m3640(3640)
  informationModel(0) asn1Module(2) asn1TypeModule(0)} DEFINITIONS IMPLICIT
TAGS ::=
BEGIN

informationModel OBJECT IDENTIFIER ::=
  {itu-t(0) recommendation(0) m(13) m3640(3640) informationModel(0)}

standardSpecificExtension OBJECT IDENTIFIER ::=
  {informationModel standardSpecificExtension(0)}

dSS1ManagedObjectClass OBJECT IDENTIFIER ::=
  {informationModel dSS1ManagedObjectClass(3)}

dSS1packageLabel OBJECT IDENTIFIER ::= {informationModel dSS1packageLabel(4)}

dSS1nameBinding OBJECT IDENTIFIER ::= {informationModel dSS1nameBinding(6)}

dSS1Attribute OBJECT IDENTIFIER ::= {informationModel dSS1Attribute(7)}

dSS1Notification OBJECT IDENTIFIER ::= {informationModel dSS1Notification(10)}

Integer ::= INTEGER

PString ::= PrintableString

TimerExpiryNetwork ::= ENUMERATED {t308(0), t309(1), t316(2), t317(3)}

MessageSequenceError ::= OCTET STRING

MessageCallRefError ::= OCTET STRING

SpecialMessageType ::= INTEGER {
  sTATUSReceived(1), rESTARTReceived(2), sTATUSTransmitted(3),
  rESTARTTransmitted(4), dlSCONNECTReceived(5), rELEASETransmitted(6),
  rELEASECOMPLETETransmitted(7), dlSCONNECTTransmitted(8), rELEASEReceived(9),
  rELEASECOMPLETEReceived(10)}

ErrorFrames ::= INTEGER {
  framesWithBadInfoField(1), framesWithBadControlField(2),
  supervisoryFramesWithBadLength(3), unnumberedFramesBadLength(4),
  framesWithInvalidReceiveSeqNumber(5), framesWithInfoFieldTooLong(6),
  fRMRReceived(7), dMFramesSendInResponseToSABME(8),
  dMFramesReceivedInResponseToSABME(9)}

InvalidFrames ::= OCTET STRING

UnexpectedFrames ::= OCTET STRING

END

-- Generated by Asnp, the ASN.1 pretty-printer of France Telecom R&D

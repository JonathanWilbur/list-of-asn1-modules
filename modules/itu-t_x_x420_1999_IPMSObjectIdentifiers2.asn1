IPMSObjectIdentifiers2 (X.420:06/1999)


-- Module IPMSObjectIdentifiers2 (X.420:06/1999)
-- See also ITU-T X.420 (06/1999)
-- See also the index of all ASN.1 assignments needed in this document

IPMSObjectIdentifiers2 {iso standard mhs(10021) ipms(7) modules(0)
  object-identifiers(0)} DEFINITIONS IMPLICIT TAGS ::=
BEGIN

-- Prologue
-- Exports everything.
IMPORTS -- nothing -- ;

ID ::= OBJECT IDENTIFIER

-- Interpersonal Messaging (ISO/IEC extensions)
id-iso-ipms ID ::=
  {iso standard mhs(10021) ipms(7)}

-- Categories
id-iso-mod ID ::= {id-iso-ipms  0} -- modules; not definitive

id-iso-cs ID ::= {id-iso-ipms  1} -- character sets

-- Modules
id-mod-object-identifiers-2 ID ::= {id-iso-mod  0} -- not definitive

id-mod-extended-body-part-types-2 ID ::= {id-iso-mod  1} -- not definitive

-- Registration Authority for General Text Character Set EITs
id-cs-eit-authority ID ::=
  {id-iso-cs  0}

END -- of IPMSObjectIdentifiers2

-- Generated by Asnp, the ASN.1 pretty-printer of France Telecom R&D

M3 (X.683:07/2002)


-- Module M3 (X.683:07/2002)
-- See also ITU-T X.683 (07/2002)
-- See also the index of all ASN.1 assignments needed in this document

M3 DEFINITIONS AUTOMATIC TAGS ::=
BEGIN

IMPORTS T1
          FROM M1;

T5 ::= T4{T1}

T4{Y} ::= SEQUENCE {a  INTEGER,
                    b  Y
}

END

-- Generated by Asnp, the ASN.1 pretty-printer of France Telecom R&D

E-health-Data-Message (X.1080.1:10/2011)


-- Module E-health-Data-Message (X.1080.1:10/2011)
-- See also ITU-T X.1080.1 (10/2011)
-- See also the index of all ASN.1 assignments needed in this document

E-health-Data-Message {joint-iso-itu-t(2) telebiometrics(42)
  e-health-protocol(3) modules(0) examples(5) data-message(1)}
  "/Telebiometrics/E_health_Protocol/Modules/Examples/Data_Message"
DEFINITIONS AUTOMATIC TAGS ::=
BEGIN

IMPORTS
  SYMBOLS, UNIT, QUANTITY
    FROM E-health-quantities-and-units {joint-iso-itu-t(2) telebiometrics(42)
      e-health-protocol(3) modules(0) quantity-and-units(4) version1(1)};

DataMessage{QUANTITY:Quantities} ::= SEQUENCE {
  quantity      QUANTITY.&id({Quantities}),
  unit          UNIT.&id({Quantities.&Units}) OPTIONAL,
  symbol        SYMBOLS.&id({Quantities.&Units.&symbols}) OPTIONAL,
  method        OBJECT IDENTIFIER,
  value         REAL,
  normalValues  NormalValues OPTIONAL,
  ...
}

NormalValues ::= SEQUENCE OF NormalValue

NormalValue ::= SEQUENCE {
  value
    CHOICE {range       SEQUENCE {minimum  REAL,
                                  maximum  REAL},
            low-limit   REAL,
            high-limit  REAL},
  conditions  SEQUENCE OF Condition OPTIONAL
}

Condition ::= SEQUENCE {
  id     CONDITION.&id({Conditions}),
  value  CONDITION.&Type({Conditions}{@id})
}

CONDITION ::= CLASS {
  &name  UniversalString,
  &id    OBJECT IDENTIFIER,
  &Type  
}WITH SYNTAX {&name
              TYPE &Type
              IDENTIFIED BY &id
}

Conditions CONDITION ::=
  {...}

END

-- Generated by Asnp, the ASN.1 pretty-printer of France Telecom R&D

M3100ASN1TypeModule7 (M.3100:04/2005)


-- Module M3100ASN1TypeModule7 (M.3100:04/2005)
-- See also ITU-T M.3100 (04/2005)
-- See also the index of all ASN.1 assignments needed in this document

M3100ASN1TypeModule7 {itu-t recommendation m gnm(3100) informationModel(0)
  asn1Modules(2) asn1Module7(6)} DEFINITIONS IMPLICIT TAGS ::=
BEGIN

-- EXPORTS everything
-- IMPORTS nothing
AttributeChoiceInteger ::= SEQUENCE {
  attributeName  GraphicString,
  minimumValue   INTEGER,
  maximumValue   INTEGER,
  granularity    INTEGER
}

AttributeChoiceReal ::= SEQUENCE {
  attributeName  GraphicString,
  minimumValue   REAL,
  maximumValue   REAL
}

Kind ::= GraphicString

ManagedElementType ::=
  SET OF CHOICE {meTypeString  GraphicString,
                 meTypeOID     OBJECT IDENTIFIER}

ModelCode ::= GraphicString

NeAliases ::= SET OF GraphicString

PortIDType ::= SEQUENCE {
  managedElement  [0]  GraphicString,
  bay             [1]  GraphicString OPTIONAL,
  shelf           [2]  GraphicString OPTIONAL,
  drawer          [3]  GraphicString OPTIONAL,
  slot            [4]  GraphicString OPTIONAL,
  port            [5]  GraphicString
}

Ranges ::=
  SET OF
    CHOICE {integerRange  [0]  AttributeChoiceInteger,
            realRange     [1]  AttributeChoiceReal}

END

-- Generated by Asnp, the ASN.1 pretty-printer of France Telecom R&D

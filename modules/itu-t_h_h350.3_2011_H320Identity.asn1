H320Identity (H.350.3:05/2011)


-- Module H320Identity (H.350.3:05/2011)
-- See also ITU-T H.350.3 (05/2011)
-- See also the index of all ASN.1 assignments needed in this document

H320Identity {itu-t(0) recommendation(0) h(8) 350 1 cr(1) h320Identity(5)
  module(4)} DEFINITIONS ::=
BEGIN

-- h320Identity Object Schema
-- Schema for representing h320Identity Object in an LDAP Directory
-- Abstract
-- This Recommendation defines the schema for representing h320Identity 
-- object in an LDAP directory [LDAPv3]. It defines schema elements
-- to represent an h320Identity object [h320Identity].
--                     .1 = Communication related work
--                     .1.5 = h320Identity
--                     .1.5.1 = attributes
--                     .1.5.2 = objectclass
--                     .1.5.3 = syntax
IMPORTS
  -- from Rec. ITU-T H.350
  h350-cr, caseIgnoreIA5Match
    FROM CommURI {itu-t(0) recommendation(0) h(8) 350 1 cr(1) commURI(1)
      module(4)}
  -- from Rec. ITU-T X.501 | ISO/IEC 9594-2
  ATTRIBUTE, OBJECT-CLASS, top
    FROM InformationFramework {joint-iso-itu-t ds(5) module(1)
      informationFramework(1) 6}
  -- from Rec. ITU-T X.520 | ISO/IEC 9594-6
  UnboundedDirectoryString, caseIgnoreMatch, caseIgnoreSubstringsMatch
    FROM SelectedAttributeTypes {joint-iso-itu-t ds(5) module(1)
      selectedAttributeTypes(5) 6};

-- Attribute Type Definitions
--    The following attribute types are defined in this Recommendation:
--        h320IdentityCC
--        h320IdentityNDC
--        h320IdentitySN
--        h320IdentityServiceLevel
--        h320IdentityExtension
h320IdentityCC ATTRIBUTE ::= {
  WITH SYNTAX             IA5String(SIZE (1..3))
  EQUALITY MATCHING RULE  caseIgnoreIA5Match
  ID                      {at  1}
}

h320IdentityNDC ATTRIBUTE ::= {
  WITH SYNTAX             IA5String(SIZE (1..15))
  EQUALITY MATCHING RULE  caseIgnoreIA5Match
  ID                      {at  4}
}

h320IdentitySN ATTRIBUTE ::= {
  WITH SYNTAX             IA5String(SIZE (1..15))
  EQUALITY MATCHING RULE  caseIgnoreIA5Match
  ID                      {at  5}
}

h320IdentityServiceLevel ATTRIBUTE ::= {
  WITH SYNTAX               UnboundedDirectoryString
  EQUALITY MATCHING RULE    caseIgnoreMatch
  SUBSTRINGS MATCHING RULE  caseIgnoreSubstringsMatch
  ID                        {at  2}
}

h320IdentityExtension ATTRIBUTE ::= {
  WITH SYNTAX               UnboundedDirectoryString
  EQUALITY MATCHING RULE    caseIgnoreMatch
  SUBSTRINGS MATCHING RULE  caseIgnoreSubstringsMatch
  ID                        {at  3}
}

-- Object Class Definitions
--    The following object class is defined in this Recommendation:
--        h320Identity
-- h320Identity
h320Identity OBJECT-CLASS ::= {
  SUBCLASS OF  {top}
  MAY CONTAIN
    {h320IdentityCC | h320IdentityNDC | h320IdentitySN |
      h320IdentityServiceLevel | h320IdentityExtension}
  ID           {oc  1}
}

h320-Id OBJECT IDENTIFIER ::= {h350-cr h320-Id(5)}

at OBJECT IDENTIFIER ::= {h320-Id at(1)}

oc OBJECT IDENTIFIER ::= {h320-Id oc(2)}

END -- end of ASN.1

-- Generated by Asnp, the ASN.1 pretty-printer of France Telecom R&D

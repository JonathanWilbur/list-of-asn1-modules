Q832-1ASN1DefinedTypesModule (Q.832.1:06/1998)


-- Module Q832-1ASN1DefinedTypesModule (Q.832.1:06/1998)
-- See also ITU-T Q.832.1 (1998) Cor. 1 (03/2001)
-- See also the index of all ASN.1 assignments needed in this document

Q832-1ASN1DefinedTypesModule {itu-t(0) recommendation(0) q(17) q832(832)
  dot(127) vb51(1) informationModel(0) asn1Modules(2) asn1DefinedTypesModule(0)
  } DEFINITIONS IMPLICIT TAGS ::=
BEGIN

-- EXPORTS everything
IMPORTS
  ObjectInstance
    FROM CMIP-1 {joint-iso-itu-t ms(9) cmip(1) modules(0) protocol(3)}
  NameType, PointerOrNull
    FROM ASN1DefinedTypesModule {itu-t recommendation m 3100
      informationModel(0) asn1Modules(2) asn1DefinedTypesModule(0)}
  ProbableCause, SpecificProblems
    FROM Attribute-ASN1Module {joint-iso-itu-t ms(9) smi(3) part2(2)
      asn1Module(2) 1}
  TpAndVpciPtrList, VpciValue
    FROM Q824-6ASN1DefinedTypesModule {itu-t recommendation q(17) ca(824)
      dot(127) bsm(6) informationModel(0) asn1Module(2) asn1TypeModule(0)}; -- end of imports

-- start of object identifier definitions
q832-1InformationModel OBJECT IDENTIFIER ::=
  {itu-t(0) recommendation(0) q(17) q832(832) dot(127) vb51(1)
   informationModel(0)}

q832-1StandardSpecificExtension OBJECT IDENTIFIER ::=
  {q832-1InformationModel standardSpecificExtension(0)}

q832-1ManagedObjectClass OBJECT IDENTIFIER ::=
  {q832-1InformationModel managedObjectClass(3)}

q832-1Package OBJECT IDENTIFIER ::= {q832-1InformationModel package(4)}

q832-1NameBinding OBJECT IDENTIFIER ::= {q832-1InformationModel nameBinding(6)}

q832-1Attribute OBJECT IDENTIFIER ::= {q832-1InformationModel attribute(7)}

q832-1Action OBJECT IDENTIFIER ::= {q832-1InformationModel action(9)}

q832-1Notification OBJECT IDENTIFIER ::=
  {q832-1InformationModel notification(10)}

vb51ProbableCause OBJECT IDENTIFIER ::= {q832-1StandardSpecificExtension 0}

vb51SpecificProblems OBJECT IDENTIFIER ::= {q832-1StandardSpecificExtension 1}

-- end of object identifier definitions
-- The value assignments for the 
-- ProbableCause parameter of the 
-- VB5.1 specific TMN communications alarm notification 
-- are specified below
rtmcProtocolError ProbableCause ::=
  globalValue:{vb51ProbableCause 1}

rtmcProtocolSyntaxError ProbableCause ::= globalValue:{vb51ProbableCause 2}

rtmcProtocolTimeOutError ProbableCause ::= globalValue:{vb51ProbableCause 3}

nonRecoverableSSCOPError ProbableCause ::= globalValue:{vb51ProbableCause 4}

-- The value assignments for the 
-- SpecificProblems parameter of the 
-- VB5.1 specific TMN communications alarm notification 
-- are specified below
protocolDiscriminatorError SpecificProblems ::=
  {oi:{vb51SpecificProblems 0}}

unrecognizedMessageType SpecificProblems ::= {oi:{vb51SpecificProblems 1}}

-- UnkMsgType RTMCProtErrCause 1
repeatedInformationElement SpecificProblems ::=
  {oi:{vb51SpecificProblems 2}}

-- RepIE RTMCProtErrCause 2
mandatoryInformationElementMissing SpecificProblems ::=
  {oi:{vb51SpecificProblems 3}}

-- MandIEMiss RTMCProtErrCause 3
unrecognizedInformationElement SpecificProblems ::=
  {oi:{vb51SpecificProblems 4}}

-- UnrecogIE RTMCProtErrCause 4
informationElementContentError SpecificProblems ::=
  {oi:{vb51SpecificProblems 5}}

-- IEContErr RTMCProtErrCause 5
informationElementNotAllowed SpecificProblems ::=
  {oi:{vb51SpecificProblems 6}}

-- IENotAllowed RTMCProtErrCause 6
messageNotCompatibleProtocolState SpecificProblems ::=
  {oi:{vb51SpecificProblems 7}}

-- MsgNotCompatWithProtState RTMCProtErrCause 7
-- other ASN1 definitions in alphabetical order
AdministrativeReason ::= INTEGER {none(0), adminPartial(1), adminFull(2)
}

CheckLspIdentificationResult ::= BOOLEAN

CheckVpciConsistencyInformation ::= INTEGER(0..65535)

CheckVpciConsistencyResult ::= CHOICE {
  localReason   NULL,
  remoteReason  RemoteReason
}

ErrorReason ::= INTEGER {none(0), error(1)}

Integer ::= INTEGER

lspActivationInitial LspActivationState ::= notActivated

LspActivationState ::= INTEGER {notActivated(0), activated(1), restarting(2)}

PartialAdministrativeState ::= ENUMERATED {
  partialLocked(0), partialUnlocked(1), partialShuttingDown(2)}

RemoteBlockingReasonVb5 ::= SEQUENCE {
  errorReason           ErrorReason,
  administrativeReason  AdministrativeReason
}

remoteBlockingReasonVb5InitialValue RemoteBlockingReasonVb5 ::=
  {errorReason none, administrativeReason adminFull}

RemoteBlockingVb5 ::= INTEGER {
  remoteBlocked(0), remoteUnblocked(1), remoteAwaitClear(2)}

remoteBlockingVb5InitialValue RemoteBlockingVb5 ::= remoteBlocked

RemoteReason ::= INTEGER {notSuccessful(0), successful(1), notPerformed(2)}

ResetRtmcResult ::= INTEGER {notSuccessful(0), successful(1)}

StartupLspResult ::= INTEGER {
  notSuccessful(0), successful(1), activating(2), restarting(3)}

END -- of ASN1DefinedTypesModule

-- Generated by Asnp, the ASN.1 pretty-printer of France Telecom R&D

M3108PartVPNASN1Module (M.3108.3:01/2001)


-- Module M3108PartVPNASN1Module (M.3108.3:01/2001)
-- See also ITU-T M.3108.3 (01/2001)
-- See also the index of all ASN.1 assignments needed in this document

M3108PartVPNASN1Module {itu-t recommendation m lcs(3108)
  vpnServiceManagement(3) informationModel(0) asn1Modules(2)
  asn1DefinedTypesModule(0)} DEFINITIONS IMPLICIT TAGS ::=
BEGIN

-- EXPORTS everything
IMPORTS
  NameType
    FROM ASN1DefinedTypesModule {itu-t(0) recommendation m gnm(3100)
      informationModel(0) asn1Modules(2) asn1DefinedTypesModule(0)}
  ServiceDescription
    FROM X790ASN1Module {itu-t(0) recommendation(0) x(24) x790(790)
      informationModel(0) asn1module(2)};

m3108PartVPNInformationModel OBJECT IDENTIFIER ::=
  {itu-t recommendation m lcs(3108) vpnServiceManagement(3) informationModel(0)}

m3108PartVPNObjectClass OBJECT IDENTIFIER ::=
  {m3108PartVPNInformationModel managedObjectClass(1)}

m3108PartVPNPackage OBJECT IDENTIFIER ::=
  {m3108PartVPNInformationModel package(2)}

m3108PartVPNAttribute OBJECT IDENTIFIER ::=
  {m3108PartVPNInformationModel attribute(3)}

m3108PartVPNNameBinding OBJECT IDENTIFIER ::=
  {m3108PartVPNInformationModel nameBinding(4)}

m3108PartVPNNotification OBJECT IDENTIFIER ::=
  {m3108PartVPNInformationModel notification(5)}

m3108PartVPNParameter OBJECT IDENTIFIER ::=
  {m3108PartVPNInformationModel parameter(6)}

m3108PartVPNAction OBJECT IDENTIFIER ::=
  {m3108PartVPNInformationModel action(7)}

Bandwidth ::= SEQUENCE {
  peakBandwidth         [0]  INTEGER OPTIONAL,
  sustainableBandwidth  [1]  INTEGER OPTIONAL,
  ...
}

CreateVpnServiceError ::= ENUMERATED {
  invalidServiceClasses(1), duplicatedVPNIdentifier(2), invalidSAG(3), ...
  }

CreateVpnLCSError ::= ENUMERATED {
  unknownServiceClass(1), requestedBandwidthNotAvailable(2),
  resourcesUnavailable(3), invalidScheduleConflict(4), contractViolation(5),
  invalidParameterValue(6), requiredParameterNotSupplied(7), nonExistentSAP(8),
  sAPnotinVPN(9), serviceClassnotinserviceClassList(10),
  invalidTerminationDate(11), ...
  }

DeleteVpnLCSError ::= ENUMERATED {
  invalidServiceID(1), unlockedAdministrativeState(2), alreadyDeleted(3),
  invalidCircuitNumber(4), notBeinginAppropriateServiceAdministrativeState(5),
  contractViolation(6), invalidVPNIdentifier(7), ...
  }

END

-- Generated by Asnp, the ASN.1 pretty-printer of France Telecom R&D

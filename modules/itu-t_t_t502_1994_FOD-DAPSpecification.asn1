FOD-DAPSpecification (T.502:11/1994)


-- Module FOD-DAPSpecification (T.502:11/1994)
-- See also ITU-T T.502 (11/1994)
-- See also the index of all ASN.1 assignments needed in this document

FOD-DAPSpecification DEFINITIONS ::=
BEGIN

EXPORTS Appl-Comm-Encoding;

Appl-Comm-Encoding ::= SEQUENCE {
  constraint-name  [0] IMPLICIT PrintableString OPTIONAL,
  external-data    [1] IMPLICIT OCTET STRING OPTIONAL
}

END

-- Generated by Asnp, the ASN.1 pretty-printer of France Telecom R&D

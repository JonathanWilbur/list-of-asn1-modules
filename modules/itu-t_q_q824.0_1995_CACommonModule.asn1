CACommonModule (Q.824.0:10/1995)


-- Module CACommonModule (Q.824.0:10/1995)
-- See also ITU-T Q.824.0 (10/1995)
-- See also the index of all ASN.1 assignments needed in this document

CACommonModule {itu-t(0) recommendation(0) q(17) ca(824) dot(127) common(0)
  informationModel(0) asn1Modules(2) cACommonModule(0)} DEFINITIONS IMPLICIT
TAGS ::=
BEGIN

--  EXPORTS Everything;
IMPORTS
  UsageState, OperationalState
    FROM Attribute-ASN1Module {joint-iso-itu-t ms(9) smi(3) part2(2)
      asn1Module(2) 1}
  ObjectInstance, ObjectClass
    FROM CMIP-1 {joint-iso-itu-t ms(9) cmip(1) modules(0) protocol(3)}
  AlarmStatus, Boolean, NameType, ObjectList, Pointer, PointerOrNull
    FROM ASN1DefinedTypesModule {itu-t recommendation m(13) gnm(3100)
      informationModel(0) asn1Modules(2) asn1DefinedTypesModule(0)};

q824-0InformationModel OBJECT IDENTIFIER ::=
  {itu-t(0) recommendation(0) q(17) ca(824) dot(127) common(0)
   informationModel(0)}

cACommonObjectClass OBJECT IDENTIFIER ::=
  {q824-0InformationModel managedObjectClass(3)}

cACommonPackage OBJECT IDENTIFIER ::= {q824-0InformationModel package(4)}

cACommonAttribute OBJECT IDENTIFIER ::= {q824-0InformationModel attribute(7)}

cACommonNameBinding OBJECT IDENTIFIER ::=
  {q824-0InformationModel nameBinding(6)}

cACommonAction OBJECT IDENTIFIER ::= {q824-0InformationModel action(9)}

--  default value definitions 
false Boolean ::= FALSE

emptySet SetOfInstances ::= {}

interceptTreatmentOrigin InterceptTreatmentOrigin ::= generic:siteTranslations

interceptTreatmentTerm InterceptTreatmentTerm ::= generic:siteTranslations

--  supporting productions 
AccessChannelPtrList ::= SET OF NameType

AccessPortPtr ::= ObjectInstance

AccessPortInterfaceIdPtr ::= SEQUENCE {
  accessPortPtr        AccessPortPtr,
  interfaceIdentifier  INTEGER(1..MAX)
}

CircuitSubgroupChannelPtrList ::= SEQUENCE OF ObjectInstance

DirectoryNumber ::= CHOICE {e164DN  [0]  E164DN,
                            x121DN  [1]  X121DN
}

DirectoryNumberList ::= SET OF DirectoryNumber

E164DN ::= SEQUENCE {
  countryCode                [0]  NumericString(SIZE (1..4)) OPTIONAL,
  nationalSignificantNumber
    [1]  SEQUENCE {nationalDestinationNumber
                     [0]  NumericString(SIZE (1..6)) OPTIONAL,
                   subscriberNumber           [1]  NumericString(SIZE (1..8))
  }
}

InterceptTreatmentOrigin ::= CHOICE {
  customized  NumericString(SIZE (1..5)),
  generic     InterceptTreatmentOriginTypes
}

InterceptTreatmentOriginTypes ::= ENUMERATED {
  siteTranslations(0), --  default value
  noDialTone(1), localAnnouncement(2), businessGroupSpecialAnnouncement(3),
  softDTEmergencyServiceBusinessOffice(4)}

InterceptTreatmentTerm ::= CHOICE {
  customized  NumericString(SIZE (1..5)),
  generic     InterceptTreatmentTermTypes
}

InterceptTreatmentTermTypes ::= ENUMERATED {
  siteTranslations(0), troubleOrSuspendServiceAnnouncement(1),
  operatorIntercept(2), dNChangeOrDisconnectAnnouncement(3),
  announceAndOperator(4), externalAutomaticInterceptSystem(5),
  businessGroupAnnouncementForDisconnectedOrTermRestrictedLines(6)}

Insert ::= CHOICE {firstElement  NULL,
                   after         ObjectInstance
}

InsertCSGChannels ::= SEQUENCE {
  insertAfter  Insert,
  newMembers   SET OF ObjectInstance
}

InsertCircuitSubgroups ::= SEQUENCE {
  insertAfterCircuitSubgroup  Insert,
  newCircuitSubgroups         SET OF CircuitSubgroup
}

Layer4InfoEntityType ::= INTEGER

Layer5InfoEntityType ::= INTEGER

Layer6InfoEntityType ::= INTEGER

Layer7InfoEntityType ::= INTEGER

ModifyCircuitSubgroup ::= SEQUENCE {
  circuitEndPointSubgroupName  ObjectInstance,
  newDelete                    INTEGER OPTIONAL,
  newPrefix                    IA5String OPTIONAL
}

NumberOfBChannels ::= INTEGER

RemoveCSGChannels ::= SET OF ObjectInstance

RemoveCircuitSubgroups ::= SET OF ObjectInstance

CircuitSubgroup ::= SEQUENCE {
  circuitEndPointSubgroupName  ObjectInstance,
  delete                       INTEGER,
  prefix                       IA5String
}

CircuitSubgroupPtrList ::= SEQUENCE OF CircuitSubgroup

SetOfInstances ::= SET OF ObjectInstance

StringName ::= GraphicString

SetOfStringNames ::= SET OF StringName

SupportedByAccessPortPtr ::= CHOICE {
  accessPortPtr             AccessPortPtr,
  accessPortInterfaceIdPtr  AccessPortInterfaceIdPtr
}

SupportedByAccessPortPtrList ::= SET OF SupportedByAccessPortPtr

X121DN ::= CHOICE {
  internationalDataNumber
    [0]  SEQUENCE {dNIC                   [0]  NumericString(SIZE (4)) OPTIONAL,
                   networkTerminalNumber  [1]  NumericString(SIZE (1..10))
  },
  internationalDataNumberIntegrated
    [1]  SEQUENCE {dCC             [0]  NumericString(SIZE (3)) OPTIONAL,
                   nationalNumber  [1]  NumericString(SIZE (1..11))},
  internationalTelexNumber
    [2]  SEQUENCE {tDC                  [0]  NumericString(SIZE (3)) OPTIONAL,
                   nationalTelexNumber  [1]  NumericString(SIZE (1..11))
  }
}

END --  Type definitions 

-- Generated by Asnp, the ASN.1 pretty-printer of France Telecom R&D

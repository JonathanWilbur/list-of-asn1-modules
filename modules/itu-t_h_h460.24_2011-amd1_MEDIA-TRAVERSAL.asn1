MEDIA-TRAVERSAL (H.460.24:05/2011)


-- Module MEDIA-TRAVERSAL (H.460.24:05/2011)
-- See also ITU-T H.460.24 (2009) Amd. 1 (05/2011)
-- See also the index of all ASN.1 assignments needed in this document

MEDIA-TRAVERSAL {itu-t(0) recommendation(0) h(8) 460 24 2 asn1-module(1)}
DEFINITIONS AUTOMATIC TAGS ::=
BEGIN

IMPORTS
  TransportAddress
    FROM MULTIMEDIA-SYSTEM-CONTROL {itu-t(0) recommendation(0) h(8) h245(245)
      version(0) 15 multimedia-system-control(0)}; -- See Rec. ITU-T H.245

AlternateAddresses ::= SEQUENCE {addresses  SEQUENCE OF AlternateAddress,
                                 ...
}

AlternateAddress ::= SEQUENCE {
  sessionID    INTEGER(0..255),
  sessionCUI   IA5String OPTIONAL,
  rtpAddress   TransportAddress OPTIONAL,
  rtcpAddress  TransportAddress OPTIONAL,
  ...
}

END

-- Generated by Asnp, the ASN.1 pretty-printer of France Telecom R&D

M3100ASN1TypeModule4 (M.3100:07/1995)


-- Module M3100ASN1TypeModule4 (M.3100:07/1995)
-- See also ITU-T M.3100 (07/1995)
-- See also the index of all ASN.1 assignments needed in this document

M3100ASN1TypeModule4 {itu-t recommendation m gnm(3100) informationModel(0)
  asn1Modules(2) asn1Module4(3)} DEFINITIONS IMPLICIT TAGS ::=
BEGIN

-- EXPORTS everything
IMPORTS
  ObjectInstance
    FROM CMIP-1 {joint-iso-itu-t ms(9) cmip(1) modules(0) protocol(3)}
  EventTime
    FROM Attribute-ASN1Module {joint-iso-itu-t ms(9) smi(3) part2(2)
      asn1Module(2) 1}
  AdditionalInformation, AlarmStatus, PerceivedSeverity, ProbableCause
    FROM Attribute-ASN1Module {joint-iso-itu-t ms(9) smi(3) part2(2)
      asn1Module(2) 1};

AlarmingResumed ::= BOOLEAN -- TRUE implies alarm reporting is resumed

ArcAffectedObjectList ::= SET OF ObjectInstance

ArcAlarmDetail ::= SEQUENCE {
  problem            ProbableCause,
  alarmStatus        AlarmStatus,
  perceivedSeverity  PerceivedSeverity OPTIONAL, -- must be present unless <unassigned> (i.e. not an alarm)
  eventTime          EventTime OPTIONAL
}

ArcAlarmDetailSet ::= SET OF ArcAlarmDetail

ArcControlRequest ::= SEQUENCE {
  time            ArcTime DEFAULT noAdjustment:NULL,
  newState        ArcState,
  additionalInfo  AdditionalInformation OPTIONAL
}

ArcDefaultNALMCDInterval ::= ArcTime

ArcDefaultNALMTIInterval ::= ArcTime

ArcInterval ::= INTEGER(0..5940) -- minutes (max of 99 hours)
                       

ArcProbableCauseList ::=
  SET OF ProbableCause -- empty set means all object probable causes

ArcState ::= ENUMERATED {
  alm(0), nalm(1), nalmQualifiedInhibit(2), nalmTimedInhibit(4)}

ArcQIStatus ::= ENUMERATED {
  notApplicable(0), nalmNotReported(1), nalmCountDown(2)}

ArcTime ::= CHOICE {
  noAdjustment  [0]  NULL,
  time          [1]  ArcInterval -- minutes
}

NotSupportedProbableCause ::= SET OF ProbableCause

END

-- Generated by Asnp, the ASN.1 pretty-printer of France Telecom R&D

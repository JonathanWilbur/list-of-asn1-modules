IN-SSF-SCF-Classes (Q.1248.2:07/2001)


-- Module IN-SSF-SCF-Classes (Q.1248.2:07/2001)
-- See also ITU-T Q.1248.2 (07/2001)
-- See also the index of all ASN.1 assignments needed in this document

IN-SSF-SCF-Classes {itu-t recommendation q 1248 modules(1)
  in-ssf-scf-classes(7) version1(0)} DEFINITIONS ::=
BEGIN

TRIGGER ::= CLASS {&Parameter  OPTIONAL,
                   &id         INTEGER UNIQUE
}WITH SYNTAX {[PARAMETER &Parameter]
              IDENTIFIED BY &id
}

--The &id field uniquely identifies a class of triggers. 
--The &Parameter field defines the ASN.1 type for representing specific parameters 
-- (e.g. criteria, scfAddress, ...)
--associated with this class of triggers.
SCF-SSF-BOUNDS ::= CLASS {
  &highLayerCompatibilityLength                INTEGER OPTIONAL,
  &minAChBillingChargingLength                 INTEGER OPTIONAL,
  &maxAChBillingChargingLength                 INTEGER OPTIONAL,
  &minBackwardGVNSLength                       INTEGER OPTIONAL,
  &maxBackwardGVNSLength                       INTEGER OPTIONAL,
  &maxBearerCapabilityLength                   INTEGER OPTIONAL,
  &minCalledDirectoryNumberLength              INTEGER OPTIONAL,
  &maxCalledDirectoryNumberLength              INTEGER OPTIONAL,
  &minCalledPartyNumberLength                  INTEGER OPTIONAL,
  &maxCalledPartyNumberLength                  INTEGER OPTIONAL,
  &minCalledPartySubaddressLength              INTEGER OPTIONAL,
  &maxCalledPartySubaddressLength              INTEGER OPTIONAL,
  &minCallingGeodeticLocationLength            INTEGER OPTIONAL,
  &maxCallingGeodeticLocationLength            INTEGER OPTIONAL,
  &minCallingPartyNumberLength                 INTEGER OPTIONAL,
  &maxCallingPartyNumberLength                 INTEGER OPTIONAL,
  &minCallingPartySubaddressLength             INTEGER OPTIONAL,
  &maxCallingPartySubaddressLength             INTEGER OPTIONAL,
  &minCallResultLength                         INTEGER OPTIONAL,
  &maxCallResultLength                         INTEGER OPTIONAL,
  &maxCallReferenceLength                      INTEGER OPTIONAL,
  &minCarrierLength                            INTEGER OPTIONAL,
  &maxCarrierLength                            INTEGER OPTIONAL,
  &minCauseLength                              INTEGER OPTIONAL,
  &maxCauseLength                              INTEGER OPTIONAL,
  &maxCNInfoLength                             INTEGER OPTIONAL,
  &minDestinationIndexLength                   INTEGER OPTIONAL,
  &maxDestinationIndexLength                   INTEGER OPTIONAL,
  &minDigitsLength                             INTEGER OPTIONAL,
  &maxDigitsLength                             INTEGER OPTIONAL,
  &minDisplayInformationLength                 INTEGER OPTIONAL,
  &maxDisplayInformationLength                 INTEGER OPTIONAL,
  &minEventSpecificInformationChargingLength   INTEGER OPTIONAL,
  &maxEventSpecificInformationChargingLength   INTEGER OPTIONAL,
  &minEventTypeChargingLength                  INTEGER OPTIONAL,
  &maxEventTypeChargingLength                  INTEGER OPTIONAL,
  &minFCIBillingChargingLength                 INTEGER OPTIONAL,
  &maxFCIBillingChargingLength                 INTEGER OPTIONAL,
  &minForwardGVNSLength                        INTEGER OPTIONAL,
  &maxForwardGVNSLength                        INTEGER OPTIONAL,
  &minGenericNameLength                        INTEGER OPTIONAL,
  &maxGenericNameLength                        INTEGER OPTIONAL,
  &minGenericNumberLength                      INTEGER OPTIONAL,
  &maxGenericNumberLength                      INTEGER OPTIONAL,
  &maxInitialTimeInterval                      INTEGER OPTIONAL,
  &maxINServiceCompatibilityIndLength          INTEGER OPTIONAL,
  &minIPAvailableLength                        INTEGER OPTIONAL,
  &maxIPAvailableLength                        INTEGER OPTIONAL,
  &minIPSSPCapabilitiesLength                  INTEGER OPTIONAL,
  &maxIPSSPCapabilitiesLength                  INTEGER OPTIONAL,
  &minISDNAccessRelatedInfoLength              INTEGER OPTIONAL,
  &maxISDNAccessRelatedInfoLength              INTEGER OPTIONAL,
  &minLocationNumberLength                     INTEGER OPTIONAL,
  &maxLocationNumberLength                     INTEGER OPTIONAL,
  &maxNbOfRoutes                               INTEGER OPTIONAL,
  &minMidCallControlInfoNum                    INTEGER OPTIONAL,
  &maxMidCallControlInfoNum                    INTEGER OPTIONAL,
  &minOriginalCalledPartyIDLength              INTEGER OPTIONAL,
  &maxOriginalCalledPartyIDLength              INTEGER OPTIONAL,
  &minReasonLength                             INTEGER OPTIONAL,
  &maxReasonLength                             INTEGER OPTIONAL,
  &minRedirectingPartyIDLength                 INTEGER OPTIONAL,
  &maxRedirectingPartyIDLength                 INTEGER OPTIONAL,
  &minRequestedUTSINum                         INTEGER OPTIONAL,
  &maxRequestedUTSINum                         INTEGER OPTIONAL,
  &minRouteListLength                          INTEGER OPTIONAL,
  &maxRouteListLength                          INTEGER OPTIONAL,
  &minRouteingNumberLength                     INTEGER OPTIONAL,
  &maxRouteingNumberLength                     INTEGER OPTIONAL,
  &minScfIDLength                              INTEGER OPTIONAL,
  &maxScfIDLength                              INTEGER OPTIONAL,
  &minSCIBillingChargingLength                 INTEGER OPTIONAL,
  &maxSCIBillingChargingLength                 INTEGER OPTIONAL,
  &minSDSSinformationLength                    INTEGER OPTIONAL,
  &maxSDSSinformationLength                    INTEGER OPTIONAL,
  &minServiceInteractionIndicatorsLength       INTEGER OPTIONAL,
  &maxServiceInteractionIndicatorsLength       INTEGER OPTIONAL,
  &minSFBillingChargingLength                  INTEGER OPTIONAL,
  &maxSFBillingChargingLength                  INTEGER OPTIONAL,
  &minUSIInformationLength                     INTEGER OPTIONAL,
  &maxUSIInformationLength                     INTEGER OPTIONAL,
  &minUSIServiceIndicatorLength                INTEGER OPTIONAL,
  &maxUSIServiceIndicatorLength                INTEGER OPTIONAL,
  &numOfBCSMEvents                             INTEGER OPTIONAL,
  &numOfBCUSMEvents                            INTEGER OPTIONAL,
  &numOfChargingEvents                         INTEGER OPTIONAL,
  &numOfCounters                               INTEGER OPTIONAL,
  &numOfCSAs                                   INTEGER OPTIONAL,
  &numOfCSs                                    INTEGER OPTIONAL,
  &numOfGenericNumbers                         INTEGER OPTIONAL,
  &numOfInfoItems                              INTEGER OPTIONAL,
  &numOfInServiceCompatibilityIndLength        INTEGER OPTIONAL,
  &numOfLegs                                   INTEGER OPTIONAL,
  &numOfMessageIDs                             INTEGER OPTIONAL,
  &maxAmount                                   INTEGER OPTIONAL,
  &maxInitialUnitIncrement                     INTEGER OPTIONAL,
  &maxScalingFactor                            INTEGER OPTIONAL,
  &maxSegmentsPerDataInterval                  INTEGER OPTIONAL,
  &ub-nbCall                                   INTEGER OPTIONAL,
  &numOfAddresses                              INTEGER OPTIONAL,
  &numOfINProfile                              INTEGER OPTIONAL,
  &numOfTriggers                               INTEGER OPTIONAL,
  &minAALPLength                               INTEGER OPTIONAL,
  &maxAALPLength                               INTEGER OPTIONAL,
  &minAdditionalATMCellRateLength              INTEGER OPTIONAL,
  &maxAdditionalATMCellRateLength              INTEGER OPTIONAL,
  &minAESACalledPartyLength                    INTEGER OPTIONAL,
  &maxAESACalledPartyLength                    INTEGER OPTIONAL,
  &minAESACallingPartyLength                   INTEGER OPTIONAL,
  &maxAESACallingPartyLength                   INTEGER OPTIONAL,
  &minATMCellRateLength                        INTEGER OPTIONAL,
  &maxATMCellRateLength                        INTEGER OPTIONAL,
  &minCDVTDescriptorLength                     INTEGER OPTIONAL,
  &maxCDVTDescriptorLength                     INTEGER OPTIONAL,
  &minConnectionIdentifierLength               INTEGER OPTIONAL,
  &maxConnectionIdentifierLength               INTEGER OPTIONAL,
  &minCumulativeTransitDelayLength             INTEGER OPTIONAL,
  &maxCumulativeTransitDelayLength             INTEGER OPTIONAL,
  &minEndToEndTDLength                         INTEGER OPTIONAL,
  &maxEndToEndTDLength                         INTEGER OPTIONAL,
  &minGenericIdentifierLength                  INTEGER OPTIONAL,
  &maxGenericIdentifierLength                  INTEGER OPTIONAL,
  &minMinAcceptableATMTrafficDescriptorLength  INTEGER OPTIONAL,
  &maxMinAcceptableATMTrafficDescriptorLength  INTEGER OPTIONAL,
  &minAlternativeATMTrafficDescriptorLength    INTEGER OPTIONAL,
  &maxAlternativeATMTrafficDescriptorLength    INTEGER OPTIONAL,
  &minQoSParameterLength                       INTEGER OPTIONAL,
  &maxQoSParameterLength                       INTEGER OPTIONAL,
  &minBroadbandBearerCapabilityLength          INTEGER OPTIONAL,
  &maxBroadbandBearerCapabilityLength          INTEGER OPTIONAL,
  &maxGlobalCallReferenceLength                INTEGER OPTIONAL,
  &maxAlternativeIdentities                    INTEGER OPTIONAL,
  &maxAlternativeIds                           INTEGER OPTIONAL
}
WITH SYNTAX {
  [HIGH-LAYER-COMPATIBILITY-LENGTH &highLayerCompatibilityLength]
  [MINIMUM-FOR-ACH-BILLING-CHARGING &minAChBillingChargingLength]
  [MAXIMUM-FOR-ACH-BILLING-CHARGING &maxAChBillingChargingLength]
  [MINIMUM-FOR-BACKWARD-GVNS &minBackwardGVNSLength]
  [MAXIMUM-FOR-BACKWARD-GVNS &maxBackwardGVNSLength]
  [MAXIMUM-FOR-BEARER-CAPABILITY &maxBearerCapabilityLength]
  [MINIMUM-FOR-CALLED-DIRECTORY-NUMBER &minCalledDirectoryNumberLength]
  [MAXIMUM-FOR-CALLED-DIRECTORY-NUMBER &maxCalledDirectoryNumberLength]
  [MINIMUM-FOR-CALLED-PARTY-NUMBER &minCalledPartyNumberLength]
  [MAXIMUM-FOR-CALLED-PARTY-NUMBER &maxCalledPartyNumberLength]
  [MINIMUM-FOR-CALLED-PARTY-SUBADDRESS &minCalledPartySubaddressLength]
  [MAXIMUM-FOR-CALLED-PARTY-SUBADDRESS &maxCalledPartySubaddressLength]
  [MINIMUM-FOR-CALLING-GEODETIC-LOCATION &minCallingGeodeticLocationLength]
  [MAXIMUM-FOR-CALLING-GEODETIC-LOCATION &maxCallingGeodeticLocationLength]
  [MINIMUM-FOR-CALLING-PARTY-NUMBER &minCallingPartyNumberLength]
  [MAXIMUM-FOR-CALLING-PARTY-NUMBER &maxCallingPartyNumberLength]
  [MINIMUM-FOR-CALLING-PARTY-SUBADDRESS &minCallingPartySubaddressLength]
  [MAXIMUM-FOR-CALLING-PARTY-SUBADDRESS &maxCallingPartySubaddressLength]
  [MINIMUM-FOR-CALL-RESULT &minCallResultLength]
  [MAXIMUM-FOR-CALL-RESULT &maxCallResultLength]
  [MINIMUM-FOR-CARRIER &minCarrierLength]
  [MAXIMUM-FOR-CARRIER &maxCarrierLength]
  [MINIMUM-FOR-CAUSE &minCauseLength]
  [MAXIMUM-FOR-CAUSE &maxCauseLength]
  [MINIMUM-FOR-DESTINATION &minDestinationIndexLength]
  [MAXIMUM-FOR-DESTINATION &maxDestinationIndexLength]
  [MINIMUM-FOR-DIGITS &minDigitsLength]
  [MAXIMUM-FOR-DIGITS &maxDigitsLength]
  [MINIMUM-FOR-DISPLAY &minDisplayInformationLength]
  [MAXIMUM-FOR-DISPLAY &maxDisplayInformationLength]
  [MINIMUM-FOR-EVENT-SPECIFIC-CHARGING
     &minEventSpecificInformationChargingLength]
  [MAXIMUM-FOR-EVENT-SPECIFIC-CHARGING
     &maxEventSpecificInformationChargingLength]
  [MINIMUM-FOR-EVENT-TYPE-CHARGING &minEventTypeChargingLength]
  [MAXIMUM-FOR-EVENT-TYPE-CHARGING &maxEventTypeChargingLength]
  [MINIMUM-FOR-FCI-BILLING-CHARGING &minFCIBillingChargingLength]
  [MAXIMUM-FOR-FCI-BILLING-CHARGING &maxFCIBillingChargingLength]
  [MINIMUM-FOR-FORWARD-GVNS &minForwardGVNSLength]
  [MAXIMUM-FOR-FORWARD-GVNS &maxForwardGVNSLength]
  [MINIMUM-FOR-GENERIC-NAME &minGenericNameLength]
  [MAXIMUM-FOR-GENERIC-NAME &maxGenericNameLength]
  [MINIMUM-FOR-GENERIC-NUMBER &minGenericNumberLength]
  [MAXIMUM-FOR-GENERIC-NUMBER &maxGenericNumberLength]
  [MAXIMUM-FOR-INITIAL-TIME-INTERVAL &maxInitialTimeInterval]
  [MAXIMUM-FOR-IN-SERVICE-COMPATIBILITY &maxINServiceCompatibilityIndLength]
  [MINIMUM-FOR-IP-AVAILABLE &minIPAvailableLength]
  [MAXIMUM-FOR-IP-AVAILABLE &maxIPAvailableLength]
  [MINIMUM-FOR-IP-SSP-CAPABILITIES &minIPSSPCapabilitiesLength]
  [MAXIMUM-FOR-IP-SSP-CAPABILITIES &maxIPSSPCapabilitiesLength]
  [MINIMUM-FOR-ISDN-ACCESS-RELATED-INFO &minISDNAccessRelatedInfoLength]
  [MAXIMUM-FOR-ISDN-ACCESS-RELATED-INFO &maxISDNAccessRelatedInfoLength]
  [MINIMUM-FOR-LOCATION-NUMBER &minLocationNumberLength]
  [MAXIMUM-FOR-LOCATION-NUMBER &maxLocationNumberLength]
  [MAXIMUM-NB-OF-ROUTES &maxNbOfRoutes]
  [MINIMUM-FOR-MID-CALL-CONTROL-INFO &minMidCallControlInfoNum]
  [MAXIMUM-FOR-MID-CALL-CONTROL-INFO &maxMidCallControlInfoNum]
  [MINIMUM-FOR-ORIGINAL-CALLED-PARTY-ID &minOriginalCalledPartyIDLength]
  [MAXIMUM-FOR-ORIGINAL-CALLED-PARTY-ID &maxOriginalCalledPartyIDLength]
  [MINIMUM-FOR-REASON &minReasonLength]
  [MAXIMUM-FOR-REASON &maxReasonLength]
  [MINIMUM-FOR-REDIRECTING-ID &minRedirectingPartyIDLength]
  [MAXIMUM-FOR-REDIRECTING-ID &maxRedirectingPartyIDLength]
  [MINIMUM-FOR-REQUESTED-UTSI-NUM &minRequestedUTSINum]
  [MAXIMUM-FOR-REQUESTED-UTSI-NUM &maxRequestedUTSINum]
  [MINIMUM-FOR-ROUTE-LIST &minRouteListLength]
  [MAXIMUM-FOR-ROUTE-LIST &maxRouteListLength]
  [MINIMUM-FOR-ROUTING-NUMBER &minRouteingNumberLength]
  [MAXIMUM-FOR-ROUTING-NUMBER &maxRouteingNumberLength]
  [MINIMUM-FOR-SCF-ID &minScfIDLength]
  [MAXIMUM-FOR-SCF-ID &maxScfIDLength]
  [MINIMUM-FOR-SCI-BILLING-CHARGING &minSCIBillingChargingLength]
  [MAXIMUM-FOR-SCI-BILLING-CHARGING &maxSCIBillingChargingLength]
  [MINIMUM-FOR-SDSS-INFORMATION &minSDSSinformationLength]
  [MAXIMUM-FOR-SDSS-INFORMATION &maxSDSSinformationLength]
  [MINIMUM-FOR-SII &minServiceInteractionIndicatorsLength]
  [MAXIMUM-FOR-SII &maxServiceInteractionIndicatorsLength]
  [MINIMUM-FOR-SF-BILLING-CHARGING &minSFBillingChargingLength]
  [MAXIMUM-FOR-SF-BILLING-CHARGING &maxSFBillingChargingLength]
  [MINIMUM-FOR-USI-INFORMATION &minUSIInformationLength]
  [MAXIMUM-FOR-USI-INFORMATION &maxUSIInformationLength]
  [MINIMUM-FOR-USI-SERVICE-INDICATOR &minUSIServiceIndicatorLength]
  [MAXIMUM-FOR-USI-SERVICE-INDICATOR &maxUSIServiceIndicatorLength]
  [NUM-OF-BCSM-EVENT &numOfBCSMEvents]
  [NUM-OF-BCUSM-EVENT &numOfBCUSMEvents]
  [NUM-OF-CHARGING-EVENT &numOfChargingEvents]
  [NUM-OF-COUNTERS &numOfCounters]
  [NUM-OF-CSAS &numOfCSAs]
  [NUM-OF-CSS &numOfCSs]
  [NUM-OF-GENERIC-NUMBERS &numOfGenericNumbers]
  [NUM-OF-INFO-ITEMS &numOfInfoItems]
  [NUM-OF-INPROFILE &numOfINProfile]
  [NUM-OF-SEVERALTRIGGER &numOfTriggers]
  [NUM-OF-IN-SERVICE-COMPATIBILITY-ID &numOfInServiceCompatibilityIndLength]
  [NUM-OF-LEGS &numOfLegs]
  [NUM-OF-MESSAGE-IDS &numOfMessageIDs]
  [MAXIMUM-FOR-AMOUNT &maxAmount]
  [MAXIMUM-FOR-CALL-REFERENCE &maxCallReferenceLength]
  [MAXIMUM-FOR-CNINFO &maxCNInfoLength]
  [MAXIMUM-FOR-INITIAL-UNIT-INCREMENT &maxInitialUnitIncrement]
  [MAXIMUM-FOR-SCALING-FACTOR &maxScalingFactor]
  [MAXIMUM-FOR-SEGMENTS-PER-DATA-INTERVAL &maxSegmentsPerDataInterval]
  [MAXIMUM-FOR-UB-NB-CALL &ub-nbCall]
  [NUM-OF-ADDRESSES &numOfAddresses]
  [MINIMUM-FOR-AAL-PARAMETERS &minAALPLength]
  [MAXIMUM-FOR-AAL-PARAMETERS &maxAALPLength]
  [MINIMUM-FOR-ADDITIONAL-ATM-CELL-RATE &minAdditionalATMCellRateLength]
  [MAXIMUM-FOR-ADDITIONAL-ATM-CELL-RATE &maxAdditionalATMCellRateLength]
  [MINIMUM-FOR-AESA-CALLED-PARTY &minAESACalledPartyLength]
  [MAXIMUM-FOR-AESA-CALLED-PARTY &maxAESACalledPartyLength]
  [MINIMUM-FOR-AESA-CALLING-PARTY &minAESACallingPartyLength]
  [MAXIMUM-FOR-AESA-CALLING-PARTY &maxAESACallingPartyLength]
  [MINIMUM-FOR-ATM-CELL-RATE &minATMCellRateLength]
  [MAXIMUM-FOR-ATM-CELL-RATE &maxATMCellRateLength]
  [MINIMUM-FOR-CDVT-DESCRIPTOR &minCDVTDescriptorLength]
  [MAXIMUM-FOR-CDVT-DESCRIPTOR &maxCDVTDescriptorLength]
  [MINIMUM-FOR-CONNECTION-IDENTIFIER &minConnectionIdentifierLength]
  [MAXIMUM-FOR-CONNECTION-IDENTIFIER &maxConnectionIdentifierLength]
  [MINIMUM-FOR-CUMULATIVE-TRANSIT-DELAY &minCumulativeTransitDelayLength]
  [MAXIMUM-FOR-CUMULATIVE-TRANSIT-DELAY &maxCumulativeTransitDelayLength]
  [MINIMUM-FOR-END-TO-END-TRANSIT-DELAY &minEndToEndTDLength]
  [MAXIMUM-FOR-END-TO-END-TRANSIT-DELAY &maxEndToEndTDLength]
  [MINIMUM-FOR-GENERIC-IDENTIFIER &minGenericIdentifierLength]
  [MAXIMUM-FOR-GENERIC-IDENTIFIER &maxGenericIdentifierLength]
  [MINIMUM-FOR-MIN-ACCEPTABLE-ATM-TRAFFIC-DESCRIPTOR
     &minMinAcceptableATMTrafficDescriptorLength]
  [MAXIMUM-FOR-MIN-ACCEPTABLE-ATM-TRAFFIC-DESCRIPTOR
     &maxMinAcceptableATMTrafficDescriptorLength]
  [MINIMUM-FOR-ALTERNATIVE-ATM-TRAFFIC-DESCRIPTOR
     &minAlternativeATMTrafficDescriptorLength]
  [MAXIMUN-FOR-ALTERNATIVE-ATM-TRAFFIC-DESCRIPTOR
     &maxAlternativeATMTrafficDescriptorLength]
  [MINIMUM-FOR-QOS-PARAMETER &minQoSParameterLength]
  [MAXIMUM-FOR-QOS-PARAMETER &maxQoSParameterLength]
  [MINIMUM-FOR-BROADBAND-BEARER-CAPABILITY
     &minBroadbandBearerCapabilityLength]
  [MAXIMUM-FOR-BROADBAND-BEARER-CAPABILITY
     &maxBroadbandBearerCapabilityLength]
  [MAXIMUM-GLOBAL-CALL-REFERENCE &maxGlobalCallReferenceLength]
  [MAXIMUM-ALTERNATIVE-IDENTITIES &maxAlternativeIdentities]
  [MAXIMUM-NB-OF-ALTERNATIVE-IDENTITIES &maxAlternativeIds]
}

END

-- Generated by Asnp, the ASN.1 pretty-printer of France Telecom R&D

GRMExample (X.725:11/1995)


-- Module GRMExample (X.725:11/1995)
-- See also ITU-T X.725 (11/1995)
-- See also the index of all ASN.1 assignments needed in this document

GRMExample {joint-iso-itu-t ms(9) smi(3) part7(7) asn1Module(2) exampleASN1(99)
  } DEFINITIONS ::=
BEGIN

IMPORTS
  GroupObjects
    FROM Attribute-ASN1Module {joint-iso-itu-t ms(9) smi(3) part2(2)
      asn1Module(2) 1};

grmEx-Role OBJECT IDENTIFIER ::=
  {joint-iso-itu-t ms(9) smi(3) part7(7) grm-Role(13) exampleRole(99)}

grmEx-RelationshipClass OBJECT IDENTIFIER ::=
  {joint-iso-itu-t ms(9) smi(3) part7(7) grm-RelationshipClass(11)
   exampleRelationshipClass(99)}

grmEx-RelationshipMapping OBJECT IDENTIFIER ::=
  {joint-iso-itu-t ms(9) smi(3) part7(7) grm-RelationshipMapping(12)
   exampleRelationshipMapping(99)}

grmEx-Object OBJECT IDENTIFIER ::=
  {joint-iso-itu-t ms(9) smi(3) part7(7) managedObjectClass(3)
   exampleObjectClass(99)}

grmEx-Attribute OBJECT IDENTIFIER ::=
  {joint-iso-itu-t ms(9) smi(3) part7(7) attribute(7) exampleAttribute(99)}

grmEx-NameBinding OBJECT IDENTIFIER ::=
  {joint-iso-itu-t ms(9) smi(3) part7(7) nameBinding(6) exampleNameBinding(99)}

grmEx-Package OBJECT IDENTIFIER ::=
  {joint-iso-itu-t ms(9) smi(3) part7(7) package(4) examplePackage(99)}

PersonName ::= GraphicString

SingleValued ::= GroupObjects(SIZE (1))

ZeroToTwo ::= INTEGER(0..2)

One ::= INTEGER(1..1)

OneToFive ::= INTEGER(1..5)

OneToMax ::= INTEGER(1..MAX)

Two ::= INTEGER(2..2)

TwoToMax ::= INTEGER(2..MAX)

END

-- Generated by Asnp, the ASN.1 pretty-printer of France Telecom R&D

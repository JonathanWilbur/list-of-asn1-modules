CAISDNOUFModule (Q.824.3:10/1995)


-- Module CAISDNOUFModule (Q.824.3:10/1995)
-- See also ITU-T Q.824.3 (10/1995)
-- See also the index of all ASN.1 assignments needed in this document

CAISDNOUFModule {itu-t(0) recommendation(0) q(17) ca(824) dot(127) isdnouf(3)
  informationModel(0) ans1Modules(2) cAISDNOUFModule(0)} DEFINITIONS IMPLICIT
TAGS ::=
BEGIN

--  EXPORTS Everything;
IMPORTS
  OperationalState
    FROM Attribute-ASN1Module {joint-iso-itu-t ms(9) smi(3) part2(2)
      asn1Module(2) 1}
  ObjectInstance, ObjectClass
    FROM CMIP-1 {joint-iso-itu-t ms(9) cmip(1) modules(0) protocol(3)}
  CUGBarring, CUGDataNetworkIdentification, CUGIndex, CUGInterlockCode,
    InterCUGaccess, PreferredCUGIndex
    FROM CAISDNSSModule {itu-t(0) recommendation(0) q(17) ca(824) dot(127)
      isdnss(2) informationModel(0) asn1Modules(2) cAISDNSSModule(0)}
  AlarmStatus, Boolean, NameType, ObjectList, Pointer, PointerOrNull
    FROM ASN1DefinedTypesModule {itu-t recommendation m(13) gnm(3100)
      informationModel(0) asn1Modules(2) asn1DefinedTypesModule(0)}
  DirectoryNumber
    FROM CACommonModule {itu-t(0) recommendation(0) q(17) ca(824) dot(127)
      common(0) informationModel(0) asn1Modules(2) cACommonModule(0)};

q824-3InformationModel OBJECT IDENTIFIER ::=
  {itu-t(0) recommendation(0) q(17) ca(824) dot(127) isdnouf(3)
   informationModel(0)}

cAISDNOUFObjectClass OBJECT IDENTIFIER ::=
  {q824-3InformationModel managedObjectClass(3)}

cAISDNOUFPackage OBJECT IDENTIFIER ::= {q824-3InformationModel package(4)}

cAISDNOUFAttribute OBJECT IDENTIFIER ::= {q824-3InformationModel attribute(7)}

cAISDNOUFNameBinding OBJECT IDENTIFIER ::=
  {q824-3InformationModel nameBinding(6)}

cAISDNOUFAction OBJECT IDENTIFIER ::= {q824-3InformationModel action(9)}

--  default value definitions 
false Boolean ::= FALSE

true Boolean ::= TRUE

null NULL ::= NULL

one INTEGER ::= 1

zero INTEGER ::= 0

minusOne INTEGER ::= -1

emptySet NULL ::= NULL

TerminalEndpointId ::= INTEGER(0..126)

TSPID ::= IA5String(SIZE (1..18))

TID ::= NumericString(SIZE (2))

--  TID has values between 00 and 62 inclusive
SPID ::= SEQUENCE {tspid  TSPID,
                   tid    TID
}

TEIOrSPID ::= CHOICE {tei   [0]  TerminalEndpointId,
                      spid  [1]  SPID
}

localChannelPtrDefault PointerOrNull ::= null:NULL

remoteChannelPtrDefault PointerOrNull ::= null:NULL

END

-- Generated by Asnp, the ASN.1 pretty-printer of France Telecom R&D

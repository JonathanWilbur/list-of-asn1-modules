Call-Completion-Operations (H.450.9:11/2000)


-- Module Call-Completion-Operations (H.450.9:11/2000)
-- See also ITU-T H.450.9 (11/2000)
-- See also the index of all ASN.1 assignments needed in this document

Call-Completion-Operations {itu-t recommendation h 450 9 version1(0)
  call-completion-operations(0)} DEFINITIONS AUTOMATIC TAGS ::=
BEGIN

IMPORTS
  OPERATION, ERROR
    FROM Remote-Operations-Information-Objects {joint-iso-itu-t
      remote-operations(4) informationObjects(5) version1(0)}
  EXTENSION, Extension{}
    FROM Manufacturer-specific-service-extension-definition {itu-t
      recommendation h 450 1 version1(0) msi-definition(18)}
  CallIdentifier
    FROM H323-MESSAGES -- see ITU-T H.225.0
      
  EndpointAddress
    FROM Addressing-Data-Elements {itu-t recommendation h 450 1 version1(0)
      addressing-data-elements(9)}
  MixedExtension, undefined
    FROM Call-Hold-Operations {itu-t recommendation h 450 4 version1(0)
      call-hold-operations(0)}
  supplementaryServiceInteractionNotAllowed
    FROM H4501-General-Error-List {itu-t recommendation h 450 1 version1(0)
      general-error-list(1)}
  BasicService
    FROM Message-Waiting-Indication-Operations {itu-t recommendation h 
      450 7 version1(0) message-waiting-operations(0)};

H323CallCompletionOperations OPERATION ::=
  {ccbsRequest | ccnrRequest | ccCancel | ccExecPossible | ccRingout |
   ccSuspend | ccResume}

ccbsRequest OPERATION ::= {
  ARGUMENT  CcRequestArg
  RESULT    CcRequestRes
  ERRORS
    {shortTermRejection | longTermRejection | undefined |
      supplementaryServiceInteractionNotAllowed}
  CODE      local:40
}

ccnrRequest OPERATION ::= {
  ARGUMENT  CcRequestArg
  RESULT    CcRequestRes
  ERRORS
    {shortTermRejection | longTermRejection | undefined |
      supplementaryServiceInteractionNotAllowed}
  CODE      local:27
}

ccCancel OPERATION ::= {
  ARGUMENT         CcArg
  OPTIONAL         TRUE
  RETURN RESULT    FALSE
  ALWAYS RESPONDS  FALSE
  CODE             local:28
}

ccExecPossible OPERATION ::= {
  ARGUMENT         CcArg
  OPTIONAL         TRUE
  RETURN RESULT    FALSE
  ALWAYS RESPONDS  FALSE
  CODE             local:29
}

ccRingout OPERATION ::= {
  ARGUMENT       CcShortArg
  OPTIONAL       TRUE
  RETURN RESULT  FALSE
  ERRORS         {remoteUserBusyAgain | failureToMatch | undefined}
  CODE           local:31
}

ccSuspend OPERATION ::= {
  ARGUMENT         CcShortArg
  OPTIONAL         TRUE
  RETURN RESULT    FALSE
  ALWAYS RESPONDS  FALSE
  CODE             local:32
}

ccResume OPERATION ::= {
  ARGUMENT         CcArg
  OPTIONAL         TRUE
  RETURN RESULT    FALSE
  ALWAYS RESPONDS  FALSE
  CODE             local:33
}

CcRequestArg ::= SEQUENCE {
  numberA                EndpointAddress,
  numberB                EndpointAddress,
  ccIdentifier           CallIdentifier OPTIONAL,
  -- If present, it shall be used as the prime mechanism for associating 
  -- the unsuccessful call, the CC Request and the CC Call.
  service                BasicService,
  can-retain-service     BOOLEAN,
  retain-sig-connection  BOOLEAN OPTIONAL,
  extension              SEQUENCE SIZE (0..255) OF MixedExtension OPTIONAL,
  ...
}

CcRequestRes ::= SEQUENCE {
  retain-service  BOOLEAN,
  extension       SEQUENCE SIZE (0..255) OF MixedExtension OPTIONAL,
  ...
}

CcArg ::= CHOICE {
  shortArg  CcShortArg, -- if signalling conection is retained
  longArg   CcLongArg, -- if connection release option applies
  ...
}

CcShortArg ::= SEQUENCE {
  ccIdentifier  CallIdentifier OPTIONAL,
  extension     SEQUENCE SIZE (0..255) OF MixedExtension OPTIONAL,
  ...
}

CcLongArg ::= SEQUENCE {
  numberA       EndpointAddress OPTIONAL,
  numberB       EndpointAddress OPTIONAL,
  ccIdentifier  CallIdentifier OPTIONAL,
  service       BasicService OPTIONAL,
  -- these elements are used to identify the proper CC Request. 
  -- The ccIdentifier if present shall be the prime mechanism for this purpose.
  extension     SEQUENCE SIZE (0..255) OF MixedExtension OPTIONAL,
  ...
}

shortTermRejection ERROR ::= {CODE  local:1010
}

longTermRejection ERROR ::= {CODE  local:1011
}

remoteUserBusyAgain ERROR ::= {CODE  local:1012
}

failureToMatch ERROR ::= {CODE  local:1013
}

END -- of Call-Completion-Operations

-- Generated by Asnp, the ASN.1 pretty-printer of France Telecom R&D

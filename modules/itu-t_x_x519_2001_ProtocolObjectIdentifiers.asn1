ProtocolObjectIdentifiers (X.519:02/2001)


-- Module ProtocolObjectIdentifiers (X.519:02/2001)
-- See also ITU-T X.519 (02/2001)
-- See also the index of all ASN.1 assignments needed in this document

ProtocolObjectIdentifiers {joint-iso-itu-t ds(5) module(1)
  protocolObjectIdentifiers(4) 4} DEFINITIONS ::=
BEGIN

-- EXPORTS All 
-- The types and values defined in this module are exported for use in the other ASN.1 modules contained 
-- within the Directory Specifications, and for the use of other applications which will use them to access 
-- Directory services. Other applications may use them for their own purposes, but this will not constrain
-- extensions and modifications needed to maintain or improve the Directory service.
IMPORTS
  -- from ITU-T Rec. X.501 | ISO/IEC 9594-2
  id-ac, id-as, id-contract, id-package, id-rosObject
    FROM UsefulDefinitions {joint-iso-itu-t ds(5) module(1)
      usefulDefinitions(0) 4};

-- ROS Objects 
id-rosObject-dua OBJECT IDENTIFIER ::= {id-rosObject 1}

id-rosObject-directory OBJECT IDENTIFIER ::= {id-rosObject 2}

id-rosObject-dapDSA OBJECT IDENTIFIER ::= {id-rosObject 3}

id-rosObject-dspDSA OBJECT IDENTIFIER ::= {id-rosObject 4}

id-rosObject-dopDSA OBJECT IDENTIFIER ::= {id-rosObject 7}

id-rosObject-initiatingConsumerDSA OBJECT IDENTIFIER ::= {id-rosObject 8}

id-rosObject-respondingSupplierDSA OBJECT IDENTIFIER ::= {id-rosObject 9}

id-rosObject-initiatingSupplierDSA OBJECT IDENTIFIER ::= {id-rosObject 10}

id-rosObject-respondingConsumerDSA OBJECT IDENTIFIER ::= {id-rosObject 11}

-- contracts 
id-contract-dap OBJECT IDENTIFIER ::= {id-contract 1}

id-contract-dsp OBJECT IDENTIFIER ::= {id-contract 2}

id-contract-shadowConsumer OBJECT IDENTIFIER ::= {id-contract 3}

id-contract-shadowSupplier OBJECT IDENTIFIER ::= {id-contract 4}

id-contract-dop OBJECT IDENTIFIER ::= {id-contract 5}

-- packages 
id-package-read OBJECT IDENTIFIER ::= {id-package 1}

id-package-search OBJECT IDENTIFIER ::= {id-package 2}

id-package-modify OBJECT IDENTIFIER ::= {id-package 3}

id-package-chainedRead OBJECT IDENTIFIER ::= {id-package 4}

id-package-chainedSearch OBJECT IDENTIFIER ::= {id-package 5}

id-package-chainedModify OBJECT IDENTIFIER ::= {id-package 6}

id-package-shadowConsumer OBJECT IDENTIFIER ::= {id-package 7}

id-package-shadowSupplier OBJECT IDENTIFIER ::= {id-package 8}

id-package-operationalBindingManagement OBJECT IDENTIFIER ::= {id-package 9}

id-package-dapConnection OBJECT IDENTIFIER ::= {id-package 10}

id-package-dspConnection OBJECT IDENTIFIER ::= {id-package 11}

id-package-dispConnection OBJECT IDENTIFIER ::= {id-package 12}

id-package-dopConnection OBJECT IDENTIFIER ::= {id-package 13}

--  application contexts 
id-ac-directoryAccessAC OBJECT IDENTIFIER ::=
  {id-ac 1}

id-ac-directorySystemAC OBJECT IDENTIFIER ::= {id-ac 2}

id-ac-directoryOperationalBindingManagementAC OBJECT IDENTIFIER ::= {id-ac 3}

id-ac-shadowConsumerInitiatedAC OBJECT IDENTIFIER ::= {id-ac 4}

id-ac-shadowSupplierInitiatedAC OBJECT IDENTIFIER ::= {id-ac 5}

id-ac-reliableShadowSupplierInitiatedAC OBJECT IDENTIFIER ::= {id-ac 6}

id-ac-reliableShadowConsumerInitiatedAC OBJECT IDENTIFIER ::= {id-ac 7}

id-ac-shadowSupplierInitiatedAsynchronousAC OBJECT IDENTIFIER ::= {id-ac 8}

id-ac-shadowConsumerInitiatedAsynchronousAC OBJECT IDENTIFIER ::= {id-ac 9}

-- id-ac-directoryAccessWith2or3seAC						OBJECT IDENTIFIER	::=	{id-ac 10}
-- id-ac-directorySystemWith2or3seAC					OBJECT IDENTIFIER	::=	{id-ac 11}
-- id-ac-shadowSupplierInitiatedWith2or3seAC				OBJECT IDENTIFIER	::=	{id-ac 12}
-- id-ac-shadowConsumerInitiatedWith2or3seAC				OBJECT IDENTIFIER	::=	{id-ac 13}
-- id-ac-reliableShadowSupplierInitiatedWith2or3seAC			OBJECT IDENTIFIER	::=	{id-ac 14}
-- id-ac-reliableShadowConsumerInitiatedWith2or3seAC			OBJECT IDENTIFIER	::=	{id-ac 15}
-- id-ac-directoryOperationalBindingManagementWith2or3seAC   	OBJECT IDENTIFIER	::=	{id-ac 16}
--  ASEs (obsolete) 
--	id-ase-readASE							OBJECT IDENTIFIER	::=	{id-ase 1}
--	id-ase-searchASE   						OBJECT IDENTIFIER	::=	{id-ase 2}
--	id-ase-modifyASE   						OBJECT IDENTIFIER	::=	{id-ase 3}
--	id-ase-chainedReadASE  					OBJECT IDENTIFIER	::=	{id-ase 4}
--	id-ase-chainedSearchASE					OBJECT IDENTIFIER	::=	{id-ase 5}
--	id-ase-chainedModifyASE					OBJECT IDENTIFIER	::=	{id-ase 6}
--	id-ase-operationalBindingManagementASE    		OBJECT IDENTIFIER	::=	{id-ase 7}
--	id-ase-shadowConsumerASE					OBJECT IDENTIFIER	::=	{id-ase 8}
--	id-ase-shadowSupplierASE  					OBJECT IDENTIFIER    ::=	{id-ase 9}
--  abstract syntaxes 
id-as-directoryAccessAS OBJECT IDENTIFIER ::=
  {id-as 1}

id-as-directorySystemAS OBJECT IDENTIFIER ::= {id-as 2}

id-as-directoryShadowAS OBJECT IDENTIFIER ::= {id-as 3}

id-as-directoryOperationalBindingManagementAS OBJECT IDENTIFIER ::= {id-as 4}

id-as-directoryReliableShadowAS OBJECT IDENTIFIER ::= {id-as 5}

id-as-reliableShadowBindingAS OBJECT IDENTIFIER ::= {id-as 6}

id-as-2or3se OBJECT IDENTIFIER ::= {id-as 7}

END -- ProtocolObjectIdentifiers

-- Generated by Asnp, the ASN.1 pretty-printer of France Telecom R&D

Connectionless-ACSE-1 (X.237:04/1995)


-- Module Connectionless-ACSE-1 (X.237:04/1995)
-- See also ITU-T X.237 (04/1995)
-- See also the index of all ASN.1 assignments needed in this document

Connectionless-ACSE-1 {joint-iso-itu-t association-control(2) module(2)
  clacse1(2) version(1)} DEFINITIONS ::=
BEGIN

--  Connectionless-ACSE-1 refers to ITU-T Rec. X.237 | ISO/IEC 10035-1
IMPORTS
  AP-title, AE-qualifier, AE-title, Authentication-value, Mechanism-name,
    ObjectSet
    FROM ACSE-1 {joint-iso-itu-t association-control(2) module(0) apdus(1)
      version1(1)};

--  The data types AP-title and AE-qualifier are imported from ITU-T Rec. X.227 | ISO/IEC 8650-1
AUDT-apdu ::= [APPLICATION 0] IMPLICIT SEQUENCE {
  protocol-version
    [0] IMPLICIT BIT STRING {version1(0)} DEFAULT {version1},
  application-context-name      [1]  Application-context-name,
  called-AP-title               [2]  AP-title OPTIONAL,
  called-AE-qualifier           [3]  AE-qualifier OPTIONAL,
  called-AP-invocation-id       [4]  AP-invocation-id OPTIONAL,
  called-AE-invocation-id       [5]  AE-invocation-id OPTIONAL,
  calling-AP-title              [6]  AP-title OPTIONAL,
  calling-AE-qualifier          [7]  AE-qualifier OPTIONAL,
  calling-AP-invocation-id      [8]  AP-invocation-id OPTIONAL,
  calling-AE-invocation-id      [9]  AE-invocation-id OPTIONAL,
  --  the following field shall only be present if the Authentication functional unit is selected
  mechanism-name                [11] IMPLICIT Mechanism-name OPTIONAL,
  --  the following field shall only be present if the Authentication functional unit is selected
  calling-authentication-value  [12] EXPLICIT Authentication-value OPTIONAL,
  implementation-information    [29] IMPLICIT GraphicString OPTIONAL,
  ...,
  ...,
  user-information
    [30] IMPLICIT SEQUENCE SIZE (1, ..., 0 | 2..MAX) OF EXTERNAL
}

Application-context-name ::= OBJECT IDENTIFIER

--  As defined in CCITT Rec. X.650 | ISO 7498-3, an application-entity title is composed of an
--  application-process title and an application-entity qualifier.  The ACSE protocol provides for the
--  transfer of an application-entity title value by the transfer of its component values.
AE-invocation-id ::= INTEGER

AP-invocation-id ::= INTEGER

END

-- Generated by Asnp, the ASN.1 pretty-printer of France Telecom R&D

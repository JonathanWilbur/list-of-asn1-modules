Telebiometrics.asn (ITU-T X.1080.1 (05/2018))-- ASN module extracted from ITU-T X.1080.1 (05/2018)Telebiometrics { joint-iso-itu-t(2) telebiometrics(42) thprot(10) part1(1) module(0) oids(0) version1(1) }
DEFINITIONS::=
BEGIN

id-telebio     OBJECT IDENTIFIER ::= { joint-iso-itu-t(2) telebiometrics(42) }

id-thprot                 OBJECT IDENTIFIER ::= { id-telebio thprot(0) }
id-tmm                    OBJECT IDENTIFIER ::= { id-telebio tmm(1) }
id-hum-phys               OBJECT IDENTIFIER ::= { id-telebio human-phy(2) }
id-obj-cat                OBJECT IDENTIFIER ::= { id-telebio obj-cat(3) }

id-measures               OBJECT IDENTIFIER ::= {id-tmm metric(1)}
id-fields-of-study        OBJECT IDENTIFIER ::= {id-tmm scientific(2)}
id-modalities             OBJECT IDENTIFIER ::= {id-tmm sensory(3)}
-- OIDs for measures
id-quantities             OBJECT IDENTIFIER ::= {id-measures quantities(1)}
id-units                  OBJECT IDENTIFIER ::= {id-measures units(2)}
id-symbols                OBJECT IDENTIFIER ::= {id-measures symbols(3)}
id-conditions             OBJECT IDENTIFIER ::= {id-measures conditions(4)}
id-methods                OBJECT IDENTIFIER ::= {id-measures methods(5)}
-- OIDs for quantities
id-quantities-physics     OBJECT IDENTIFIER ::= {id-quantities physics(1)}
id-quantities-chemistry   OBJECT IDENTIFIER ::= {id-quantities chemistry(2)}
id-quantities-biology     OBJECT IDENTIFIER ::= {id-quantities biology(3)}
id-quantities-culturology OBJECT IDENTIFIER ::= {id-quantities culturology(4)}
id-quantities-psychology  OBJECT IDENTIFIER ::= {id-quantities psychology(5)}
-- OIDs for methods
id-methods-physics        OBJECT IDENTIFIER ::= {id-methods physics(1)}
id-methods-chemistry      OBJECT IDENTIFIER ::= {id-methods chemistry(2)}
id-methods-biology        OBJECT IDENTIFIER ::= {id-methods biology(3)}
id-methods-culturology    OBJECT IDENTIFIER ::= {id-methods culturology(4)}
id-methods-psychology     OBJECT IDENTIFIER ::= {id-methods psychology(5)}
-- OIDs for fields of study
id-physics                OBJECT IDENTIFIER ::= {id-fields-of-study physics(1)}
id-chemistry              OBJECT IDENTIFIER ::= {id-fields-of-study
                                                 chemistry(2)}
id-biology                OBJECT IDENTIFIER ::= {id-fields-of-study biology(3)}
id-culturology            OBJECT IDENTIFIER ::= {id-fields-of-study
                                                 culturology(4)}
id-psychology             OBJECT IDENTIFIER ::= {id-fields-of-study
                                                 psychology(5)}
-- OIDs for modalities
id-tango                  OBJECT IDENTIFIER ::= {id-modalities tango(1)}
id-video                  OBJECT IDENTIFIER ::= {id-modalities video(2)}
id-audio                  OBJECT IDENTIFIER ::= {id-modalities audio(3)}
id-chemo                  OBJECT IDENTIFIER ::= {id-modalities chemo(4)}
id-radio                  OBJECT IDENTIFIER ::= {id-modalities radio(5)}
id-calor                  OBJECT IDENTIFIER ::= {id-modalities calor(6)}
id-electro                OBJECT IDENTIFIER ::= {id-modalities electro(7)}

END

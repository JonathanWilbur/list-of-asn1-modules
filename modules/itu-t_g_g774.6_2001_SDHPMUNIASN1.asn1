SDHPMUNIASN1 (G.774.6:02/2001)


-- Module SDHPMUNIASN1 (G.774.6:02/2001)
-- See also ITU-T G.774.6 (02/2001)
-- See also the index of all ASN.1 assignments needed in this document

SDHPMUNIASN1 {itu-t(0) recommendation(0) g(7) g774(774) hyphen(127) pmUni(6)
  informationModel(0) asn1Module(2) sdhpmUni(0)} DEFINITIONS IMPLICIT TAGS ::=
BEGIN

-- EXPORTS everything
IMPORTS
  SDHGranularityPeriod, SDHPVGranularityPeriod
    FROM SDHPMASN1 {itu-t(0) recommendation(0) g(7) g774(774) hyphen(127) 
      pm(1) informationModel(0) asn1Module(2) sdhpm(0)}
  TimePeriod
    FROM MetricModule {joint-iso-itu-t ms(9) function(2) part11(11)
      asn1Module(2) 0};

sdhPMUni OBJECT IDENTIFIER ::=
  {itu-t(0) recommendation(0) g(7) g774(774) hyphen(127) pmUni(6)
   informationModel(0)}

g774-6MObjectClass OBJECT IDENTIFIER ::= {sdhPMUni managedObjectClass(3)}

g774-6Attribute OBJECT IDENTIFIER ::= {sdhPMUni attribute(7)}

g774-6NameBinding OBJECT IDENTIFIER ::= {sdhPMUni nameBinding(6)}

g774-6Package OBJECT IDENTIFIER ::= {sdhPMUni package(4)}

sdhPM OBJECT IDENTIFIER ::=
  {itu-t(0) recommendation(0) g(7) g774(774) hyphen(127) pm(1)
   informationModel(0)}

g774-01MObjectClass OBJECT IDENTIFIER ::= {sdhPM managedObjectClass(3)}

g774-01Attribute OBJECT IDENTIFIER ::= {sdhPM attribute(7)}

g774-01NameBinding OBJECT IDENTIFIER ::= {sdhPM nameBinding(6)}

g774-01Package OBJECT IDENTIFIER ::= {sdhPM package(4)}

END -- end of SDHPMUNIASN1

-- Generated by Asnp, the ASN.1 pretty-printer of France Telecom R&D

RepertoireASN1Module (X.750:10/1996)


-- Module RepertoireASN1Module (X.750:10/1996)
-- See also ITU-T X.750 (1996) Technical Cor. 1 (02/2000)
-- See also the index of all ASN.1 assignments needed in this document

RepertoireASN1Module {joint-iso-itu-t(2) ms(9) function(2) part16(16)
  asn1Modules(2) 0} DEFINITIONS IMPLICIT TAGS ::=
BEGIN

-- EXPORTS everything;
IMPORTS
  DMI-TYPE-IDENTIFIER, NameBinding, Packages
    FROM Attribute-ASN1Module {joint-iso-itu-t(2) ms(9) smi(3) part2(2)
      asn1Module(2) 1}-- itu-t Rec. X.721 | ISO/IEC 10165-2
  ;

GdmoObjectClass ::= OBJECT IDENTIFIER

MKMF-VALUES ::= DMI-TYPE-IDENTIFIER

ImplementedValues ::=
  SET OF
    SEQUENCE {attributeId   MKMF-VALUES.&id({ImplementedValuesSet}),
              defaultValue
                [1] EXPLICIT MKMF-VALUES.&Value
                               ({ImplementedValuesSet}{@.attributeId}) OPTIONAL,
              initialValue
                [2] EXPLICIT MKMF-VALUES.&Value
                               ({ImplementedValuesSet}{@.attributeId}) OPTIONAL,
              minValue
                [3] EXPLICIT MKMF-VALUES.&Value
                               ({ImplementedValuesSet}{@.attributeId}) OPTIONAL,
              maxValue
                [4] EXPLICIT MKMF-VALUES.&Value
                               ({ImplementedValuesSet}{@.attributeId}) OPTIONAL
    }

ImplementedValuesSet MKMF-VALUES ::=
  {...}

ManagedObjectClassRepertoireId ::= GdmoObjectClass

RepertoireId ::= GraphicString

SupportedCmipProfiles ::= BIT STRING {
  aom10(0), -- the managed system supports ISP 11183-1
  aom11(1), -- the managed system supports ISP 11183-3
  aom12(2)} -- the managed system supports ISP 11183-2

SupportedConditionalPackageList ::= Packages

SupportedManagedObjectClassList ::= SET OF GdmoObjectClass

SupportedNameBindingList ::= SET OF NameBinding

SupportedRelationshipClassList ::= SET OF OBJECT IDENTIFIER

END

-- Generated by Asnp, the ASN.1 pretty-printer of France Telecom R&D

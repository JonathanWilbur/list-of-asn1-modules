E-health-setup (X.1080.1:10/2011)


-- Module E-health-setup (X.1080.1:10/2011)
-- See also ITU-T X.1080.1 (10/2011)
-- See also the index of all ASN.1 assignments needed in this document

E-health-setup {joint-iso-itu-t(2) telebiometrics(42) e-health-protocol(3)
  modules(0) set-up(1) version1(1)}
  "/Telebiometrics/E_Health_Protocol/Modules/Setup/Version1"
  DEFINITIONS AUTOMATIC TAGS ::=
BEGIN

IMPORTS
  CR-SEQUENCE, CR-Sequences
    FROM E-health-command-response {joint-iso-itu-t(2) telebiometrics(42)
      e-health-protocol(3) modules(0) command-response(3) version1(1)}
  SIMPLE-MESSAGE, Simple-Messages
    FROM E-health-send-and-ack {joint-iso-itu-t(2) telebiometrics(42)
      e-health-protocol(3) modules(0) send-and-ack(2) version1(1)};

-- SetUp-Message-Request and Response for simple messages and for interactive
-- message sequences
E-health-SetUp-Message-Request ::= CHOICE {
  simple       SIMPLE-MESSAGE.&id({Simple-Messages}),
  interactive  CR-SEQUENCE.&id({CR-Sequences}),
  ...
} -- Top-level type

E-health-SetUp-Message-Response ::= CHOICE {
  simple       BOOLEAN-- True is OK, False is Reject-- ,
  -- Only for response to a simple Request
  interactive
    CHOICE {accept              NULL,
            conditional-accept
              SEQUENCE {id
                          CR-SEQUENCE.&id({CR-Sequences}),
                        reduced-requirements
                          CR-SEQUENCE.&requirements({CR-Sequences}{@.id}),
                        voice-options         OBJECT IDENTIFIER,
                        video-options         OBJECT IDENTIFIER},
            reject              NULL}
}

EncryptionOptions ::= BOOLEAN

IntegrityOptions ::= BOOLEAN

END

-- Generated by Asnp, the ASN.1 pretty-printer of France Telecom R&D

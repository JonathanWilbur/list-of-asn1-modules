PHLM (X.281:06/1999)


-- Module PHLM (X.281:06/1999)
-- See also ITU-T X.281 (06/1999)
-- See also the index of all ASN.1 assignments needed in this document

PHLM {joint-iso-itu-t physical-layer(18) management(0) asn1Module(2) 0}
DEFINITIONS IMPLICIT TAGS ::=
BEGIN

IMPORTS
  GroupObjects
    FROM Attribute-ASN1Module {joint-iso-itu-t ms(9) smi(3) part2(2)
      asn1Module(2) 1}
  SetInfoStatus, AttributeId, ObjectInstance
    FROM CMIP-1 {joint-iso-itu-t ms(9) cmip(1) modules(0) protocol(3)};

--  Object identifier definitions
physical-layer OBJECT IDENTIFIER ::=
  {joint-iso-itu-t physical-layer(18)}

phloi OBJECT IDENTIFIER ::= {physical-layer management(0)}

sseoi OBJECT IDENTIFIER ::= {phloi standardSpecificExtension(0)}

moi OBJECT IDENTIFIER ::= {phloi objectClass(3)}

poi OBJECT IDENTIFIER ::= {phloi package(4)}

proi OBJECT IDENTIFIER ::= {phloi parameter(5)}

nboi OBJECT IDENTIFIER ::= {phloi nameBinding(6)}

aoi OBJECT IDENTIFIER ::= {phloi attribute(7)}

agoi OBJECT IDENTIFIER ::= {phloi attributeGroup(8)}

acoi OBJECT IDENTIFIER ::= {phloi action(9)}

noi OBJECT IDENTIFIER ::= {phloi notification(10)}

--  Other definitions
physicalSubsystemId-Value GraphicString ::=
  "physicalSubsystem"

CRCErrorReceived ::= INTEGER

BitErrors ::= INTEGER

BitErrorsThreshold ::= SEQUENCE {mantissa  [1]  INTEGER,
                                 exponent  [2]  INTEGER
}

CRCErrorTransmitted ::= INTEGER

DataCircuitType ::= ENUMERATED {end-system(0), relay-system(1)}

PhysicalEntityTitle ::= SET OF GraphicString

PhysicalInterfaceStandard ::= OCTET STRING

PhysicalInterfaceType ::= OCTET STRING

PhysicalMediaNames ::= OCTET STRING

SynchronizationMode ::= ENUMERATED {synchronous(0), asynchronous(1)}

TransmissionCoding ::= OCTET STRING

TransmissionMode ::= ENUMERATED {simplex(0), duplex(1)}

TransmissionRate ::= SEQUENCE {mantissa  [1]  INTEGER,
                               exponent  [2]  INTEGER
}

PortNumber ::= INTEGER

EndpointIdentifier ::= OCTET STRING

ConnectionError ::= OCTET STRING

ConnectionEstablished ::= OCTET STRING

BitErrorThresholdReached ::= OCTET STRING

LossOfSignal ::= OCTET STRING

LossOfSynchronization ::= OCTET STRING

END

-- Generated by Asnp, the ASN.1 pretty-printer of France Telecom R&D

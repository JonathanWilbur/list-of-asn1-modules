STASE-A-ASSOCIATE-Information (Q.813:06/1998)


-- Module STASE-A-ASSOCIATE-Information (Q.813:06/1998)
-- See also ITU-T Q.813 (06/1998)
-- See also the index of all ASN.1 assignments needed in this document

STASE-A-ASSOCIATE-Information {itu-t recommendation q(17) q813(813) stase(1)
  stase-pci(0) stase-userinfo(1)} DEFINITIONS IMPLICIT TAGS ::=
BEGIN

-- EXPORTS everything
IMPORTS
  SenderId, ReceiverId, Signature, KeyId, PublicKeyCertificate,
    EncryptionCertificate, SignatureCertificate,
    EncryptedAuthenticatedSymmetricKey
    FROM Secure-Remote-Operations-APDUs {itu-t recommendation q(17) q813(813)
      stase(1) stase-pci(0) stase-data(2)};

EncryptionParametersSelection ::= SET {
  symmetricKeyIds                      [0]  SET OF KeyId OPTIONAL,
  publicKeyIds                         [1]  SET OF KeyId OPTIONAL,
  sealKeyIds                           [2]  SET OF KeyId OPTIONAL,
  signatureKeyIds                      [3]  SET OF KeyId OPTIONAL,
  passwordIds                          [4]  SET OF KeyId OPTIONAL,
  initializationVector                 [5]  OCTET STRING(SIZE (8)) OPTIONAL,
  feedBackBits                         [6]  INTEGER(1..63) OPTIONAL,
  -- for k-bit output feedback mode or k-bit cipher feedback mode of DES
  symmetricAlgorithms                  [7]  SET OF OBJECT IDENTIFIER OPTIONAL,
  publicKeyAlgorithms                  [8]  SET OF OBJECT IDENTIFIER OPTIONAL,
  signatureAlgorithms                  [9]  SET OF OBJECT IDENTIFIER OPTIONAL,
  sealAlgorithms                       [10]  SET OF OBJECT IDENTIFIER OPTIONAL,
  hashAlgorithms                       [11]  SET OF OBJECT IDENTIFIER OPTIONAL,
  keyDigest
    [12]  OCTET STRING(SIZE (8..64)) OPTIONAL,
  -- for verification of public keys
  blockSize                            [13]  INTEGER OPTIONAL,
  -- for square mod-n hashing
  keySizes                             [14]  SET OF INTEGER OPTIONAL,
  -- for RSA
  publicKeys
    [15]  SET OF SEQUENCE {modulus   INTEGER,
                           exponent  INTEGER} OPTIONAL,
  sequenceNumber                       [16]  INTEGER OPTIONAL,
  timeStamp                            [17]  GeneralizedTime OPTIONAL,
  encryptedKey
    [18]  OCTET STRING(SIZE (64..128)) OPTIONAL,
  -- symmetric session key, encrypted with Key-Encryption-Key
  encryptedSymmetricKey                [19]  INTEGER OPTIONAL,
  -- symmetric session key, encrypted with the receiver's public key
  keyEncryptionKey
    [20]  SEQUENCE (SIZE (1..3)) OF KeyId OPTIONAL,
  -- one to three symmetric keys used for encrypting a session key
  keyListIds                           [21]  SET OF KeyListId OPTIONAL,
  -- list of encryption keys that can be used during the association
  encryptionCertificate
    [22]  SET OF EncryptionCertificate OPTIONAL,
  -- X.509 certificates or certification paths of the sender's public keys used for encryption only
  signatureCertificate
    [23]  SET OF SignatureCertificate OPTIONAL,
  -- X.509 certificates or certification paths of the sender's public keys used for digital signatures only 
  encryptedAuthenticatedSymmetricKeys
    [24]  SET OF EncryptedAuthenticatedSymmetricKey OPTIONAL,
  -- symmetric session key, encrypted with the receiver's public key and signed with sender's key
  macAlgorithms                        [25]  SET OF OBJECT IDENTIFIER OPTIONAL,
  publicKeyCertificate
    [26]  SET OF PublicKeyCertificate OPTIONAL,
  -- X.509 certificates or certification paths of the sender's public keys with no usage restrictions 
  ...
}

-- EncryptionParametersSelection is optionally used during association setup to negotiate which algorithms and other parameters will be supported during the association. It is not used in STASE-ROSE PDUs. 
KeyListId ::= CHOICE {
  identifier  OBJECT IDENTIFIER,
  name        GraphicString,
  number      INTEGER
}

END

-- Generated by Asnp, the ASN.1 pretty-printer of France Telecom R&D

M2.asn: ITU-T X.683 (11/2008) -- ASN module extracted from ITU-T X.683 (11/2008)M2 DEFINITIONS EXPLICIT TAGS ::= BEGIN
	IMPORTS T1 FROM  M1;
	T3 ::= T2{T1}
	T2{X} ::= SEQUENCE {
	a	INTEGER,
	b	X
}
END

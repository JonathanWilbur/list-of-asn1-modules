Example3-EDM


-- Generated by Ecnp, the pretty-printer of France Telecom R&amp;D

Example3-EDM {joint-iso-itu-t(2) asn1(1) ecn(4) examples(5) edm-module3(10)}
ENCODING-DEFINITIONS ::=
BEGIN

EXPORTS Example3Encodings;

RENAMES
  #OPTIONAL AS #Sequence2-optional IN #Sequence2 
  #OCTET-STRING AS #Octets3 IN ALL 
  #OPTIONAL AS #Sequence3-optional IN #Sequence3 
  #TAG AS #TAG-4-bits IN #Sequence3 
    FROM Example3-ASN1-Module {joint-iso-itu-t(2) asn1(1) ecn(4) examples(5)
      asn1-module3(9)};

Example3Encodings #ENCODINGS ::= {
  sequence1-optional-encoding |
   -- etc.
   sequenceOf-encoding}

-- etc.
END

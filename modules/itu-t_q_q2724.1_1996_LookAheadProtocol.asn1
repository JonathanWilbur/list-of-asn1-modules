LookAheadProtocol (Q.2724.1:07/1996)


-- Module LookAheadProtocol (Q.2724.1:07/1996)
-- See also ITU-T Q.2724.1 (07/1996)
-- See also the index of all ASN.1 assignments needed in this document

LookAheadProtocol {itu-t(0) recommendation(0) q(17) q2724(2724) q2724-1(1)
  modules(0) operations-and-errors(1) version1(0)} DEFINITIONS IMPLICIT TAGS
::=
BEGIN

IMPORTS --, 
  OPERATION --ERROR
    FROM TCAPMessages {itu-t recommendation q 773 modules(2) messages(1)
      version3(3)}
  -- white book TCAP
  AALParameters, AdditionalATMCellRateparameterfield, ATMCellRate,
    BroadbandBearerCapability, BroadbandHighLayerInfo, BroadbandLowLayerInfo,
    AESAForCalledParty, CalledPartyNumber, CalledPartySubaddress,
    CauseIndicators, NarrowbandBearerCapability, NarrowbandHighLayerCompa,
    NarrowbandLowLayerCompa, OAMTrafficDescriptor
    FROM LookAheadParameters {itu-t(0) recommendation(0) q(17) q2724(2724)
      q2724-1(1) modules(0) parameters(2) version1(0)}
  systemFailure, taskRefused
    FROM IN-CS-1-Errors {itu-t recommendation q 1218 modules(0) cs-1-errors(1)
      version1(0)};

lookahead OPERATION ::= {
  ARGUMENT
    SET {aALParameters                        [71]  AALParameters OPTIONAL,
         additionalATMCellRateparameterfield
           [90]  AdditionalATMCellRateparameterfield OPTIONAL,
         aTMCellRate                          [8]  ATMCellRate OPTIONAL,
         broadbandBearerCapability
           [80]  BroadbandBearerCapability OPTIONAL,
         broadbandHighLayerInfo
           [70]  BroadbandHighLayerInfo OPTIONAL,
         broadbandLowLayerInfo
           [79]  BroadbandLowLayerInfo OPTIONAL,
         aESAForCalledParty                   [88]  AESAForCalledParty OPTIONAL,
         calledPartyNumber                    [4]  CalledPartyNumber,
         calledPartySubaddress
           [21]  CalledPartySubaddress OPTIONAL,
         narrowbandBearerCapability
           [29]  NarrowbandBearerCapability OPTIONAL,
         narrowbandHighLayerCompa
           [52]  NarrowbandHighLayerCompa OPTIONAL,
         narrowbandLowLayerCompa
           [37]  NarrowbandLowLayerCompa OPTIONAL,
         oAMTrafficDescriptor
           [72]  OAMTrafficDescriptor OPTIONAL}
  RESULT
    SET {causeIndicators  [18]  CauseIndicators OPTIONAL,
         lookResult       [94]  LookResult OPTIONAL}
  ERRORS    {systemFailure | taskRefused}


-- The operation could not be completed due to a system 
-- failure at the serving physical entity.
-- An entity normally capable of the task requested cannot or 
-- chooses not to perform the task at this time. 
-- This include errors situations like congestion.
}

LookResult ::= ENUMERATED {
  compatibleAndFree(0), compatibleAndBusy(1), incompatible(2)}

--object identifier path
lookAheadOID OBJECT IDENTIFIER ::=
  {itu-t recommendation q 2724 1 operations-and-errors(1)}

--operation values
--lookAhead LookAhead ::=  globalValue {lookAheadOID lookahead(1)}
--ERROR codes
--systemFailure	SystemFailure	::= globalValue {lookAheadOID systemfailure(2)}
--taskRefused	TaskRefused	::= globalValue {lookAheadOID taskrefused(3)}
--	timer T-la = 10 sec	It is used to protect application against excessive delay in
--				response from the next exchange or terminating user.
END

-- Generated by Asnp, the ASN.1 pretty-printer of France Telecom R&D

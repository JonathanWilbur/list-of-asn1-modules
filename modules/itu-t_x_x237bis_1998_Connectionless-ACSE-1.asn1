Connectionless-ACSE-1 (X.237 bis:09/1998)


-- Module Connectionless-ACSE-1 (X.237 bis:09/1998)
-- See also ITU-T X.237 bis (09/1998)
-- See also the index of all ASN.1 assignments needed in this document

Connectionless-ACSE-1 {joint-iso-itu-t association-control(2) module(2)
  clacse1(2) version(1)} DEFINITIONS ::=
BEGIN

-- Connectionless-ACSE-2 refers to ITU-T Rec. X.237 bis | ISO/IEC15955.
IMPORTS
  AP-title, AE-qualifier, AE-title, Authentication-value, Mechanism-name,
    ObjectSet
    FROM ACSE-1 {joint-iso-itu-t association-control(2) modules(0) acse1(1)
      version(1)};

-- The data types AP-title and AE-qualifier are imported from ITU-T Rec. X.227 bis | ISO/IEC 15954.
AUDT-apdu ::= [APPLICATION 0] IMPLICIT SEQUENCE {
  protocol-version
    [0] IMPLICIT BIT STRING {version1(0)} DEFAULT {version1},
  aSO-context                   [1]  ASO-context-name OPTIONAL,
  called-AP-title               [2]  AP-title OPTIONAL,
  called-AE-qualifier           [3]  AE-qualifier OPTIONAL,
  called-AP-invocation-id       [4]  AP-invocation-id OPTIONAL,
  called-AE-invocation-id       [5]  AE-invocation-id OPTIONAL,
  calling-AP-title              [6]  AP-title OPTIONAL,
  calling-AE-qualifier          [7]  AE-qualifier OPTIONAL,
  calling-AP-invocation-id      [8]  AP-invocation-id OPTIONAL,
  calling-AE-invocation-id      [9]  AE-invocation-id OPTIONAL,
  -- The following field shall only be used if the Authentication functional unit is selected.
  mechanism-name                [11] IMPLICIT Mechanism-name OPTIONAL,
  -- The following field shall only be used if the Authentication functional unit is selected.
  calling-authentication-value  [12] EXPLICIT Authentication-value OPTIONAL,
  p-context                     [14] IMPLICIT Default-P-context OPTIONAL,
  implementation-information    [29] IMPLICIT GraphicString OPTIONAL,
  ...,
  ...,
  user-information
    [30] IMPLICIT SEQUENCE SIZE (1, ..., 0 | 2..MAX) OF EXTERNAL
}

ASO-context-name ::= OBJECT IDENTIFIER

Application-context-name ::= ASO-context-name

-- As defined in ITU-T Rec. X.650 | ISO/IEC 7498-3, an application-entity title
-- is composed of an application-process title and
-- an application-entity qualifier. The ACSE protocol provides for the transfer of an
-- application-entity title value
-- by the transfer of its component values.
AE-invocation-id ::= INTEGER

AP-invocation-id ::= INTEGER

Default-P-context ::= SEQUENCE {
  abstract-syntax  [0] IMPLICIT Abstract-syntax-name OPTIONAL,
  transfer-syntax  [1] IMPLICIT Transfer-syntax-name
}

Abstract-syntax-name ::= OBJECT IDENTIFIER

Transfer-syntax-name ::= OBJECT IDENTIFIER

END

-- Generated by Asnp, the ASN.1 pretty-printer of France Telecom R&amp;D

E-health-quantities-and-units (X.1080.1:10/2011)


-- Module E-health-quantities-and-units (X.1080.1:10/2011)
-- See also ITU-T X.1080.1 (10/2011)
-- See also the index of all ASN.1 assignments needed in this document

E-health-quantities-and-units {joint-iso-itu-t(2) telebiometrics(42)
  e-health-protocol(3) modules(0) quantity-and-units(4) version1(1)}
  "/Telebiometrics/E_health_Protocol/Modules/Quantities_And_Units/Version1"
DEFINITIONS AUTOMATIC TAGS ::=
BEGIN

SYMBOLS ::= CLASS {
  &String            UniversalString,
  &attributes        StringAttributes OPTIONAL,
  &id                OBJECT IDENTIFIER UNIQUE,
  &relative-oid-iri  RELATIVE-OID-IRI
}
WITH SYNTAX {
  &String
  [WITH ATTRIBUTES &attributes]
  IDENTIFIED BY &id
  AND &relative-oid-iri
}

StringAttributes ::= BIT STRING {italic(0), betweenParenthesis(1)}

UNIT ::= CLASS {
  &name              PrintableString,
  &symbols           SYMBOLS,
  &id                OBJECT IDENTIFIER UNIQUE,
  &relative-oid-iri  RELATIVE-OID-IRI,
  &Units1            UNIT OPTIONAL,
  &Units2            UNIT OPTIONAL,
  &multipleBaseUnit  UNIT OPTIONAL,
  &multipleFactor    REAL
                           (WITH COMPONENTS {
                              ...,
                              mantissa  (1),
                              base      (10)
                            }) OPTIONAL
}
WITH SYNTAX {
  &name
  USING SYMBOLS &symbols
  IDENTIFIED BY &id
  AND &relative-oid-iri
  [DERIVED BY
   [PRODUCT OF &Units1]
   [DIVIDED BY &Units2]]
  [MULTIPLE OF &multipleBaseUnit
   WITH FACTOR &multipleFactor]
}

QUANTITY ::= CLASS {
  &name              PrintableString,
  &frenchName        UniversalString OPTIONAL,
  &symbols           SYMBOLS,
  &Units             UNIT,
  &Modalities        OBJECT IDENTIFIER,
  &direction         ENUMERATED {in, out} OPTIONAL,
  &id                OBJECT IDENTIFIER UNIQUE,
  &relative-oid-iri  RELATIVE-OID-IRI
}
WITH SYNTAX {
  &name
  [FRENCH &frenchName]
  USING SYMBOLS &symbols
  MEASURED IN &Units
  FOR MODALITIES &Modalities
  [DIRECTION &direction]
  IDENTIFIED BY &id
  AND &relative-oid-iri
}

END

-- Generated by Asnp, the ASN.1 pretty-printer of France Telecom R&D

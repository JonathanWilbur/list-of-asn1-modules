DirectoryIDMProtocols (X.519:08/2005)


-- Module DirectoryIDMProtocols (X.519:08/2005)
-- See also the README file
-- See also the index of all ASN.1 assignments needed in this document

DirectoryIDMProtocols {joint-iso-itu-t ds(5) module(1)
  directoryIDMProtocols(31) 5} DEFINITIONS ::=
BEGIN

-- EXPORTS All 
-- The types and values defined in this module are exported for use in the other ASN.1 modules contained 
-- within the Directory Specifications, and for the use of other applications which will use them to access 
-- Directory services. Other applications may use them for their own purposes, but this will not constrain
-- extensions and modifications needed to maintain or improve the Directory service.
IMPORTS
  -- from ITU-T Rec. X.501 | ISO/IEC 9594-2
  directoryAbstractService, distributedOperations,
    directoryShadowAbstractService, id-idm, iDMProtocolSpecification,
    opBindingManagement
    FROM UsefulDefinitions {joint-iso-itu-t ds(5) module(1)
      usefulDefinitions(0) 5}
  establishOperationalBinding, modifyOperationalBinding,
    terminateOperationalBinding, dSAOperationalBindingManagementBind
    FROM OperationalBindingManagement opBindingManagement
  -- from ITU-T Rec. X.511 | ISO/IEC 9594-3
  abandon, addEntry, compare, directoryBind, list, modifyDN, modifyEntry, 
    read, removeEntry, search
    FROM DirectoryAbstractService directoryAbstractService
  -- from ITU-T Rec. X.518 | ISO/IEC 9594-4
  chainedAbandon, chainedAddEntry, chainedCompare, chainedList,
    chainedModifyDN, chainedModifyEntry, chainedRead, chainedRemoveEntry,
    chainedSearch, dSABind
    FROM DistributedOperations distributedOperations
  -- from ITU-T Rec. X.519 | ISO/IEC 9594-5
  IDM-PDU, IDM-PROTOCOL
    FROM IDMProtocolSpecification iDMProtocolSpecification
  -- from ITU-T Rec. X.525 | ISO/IEC 9594-9
  coordinateShadowUpdate, requestShadowUpdate, updateShadow, dSAShadowBind
    FROM DirectoryShadowAbstractService directoryShadowAbstractService;

-- IDM protocols 
DAP-IDM-PDUs ::= IDM-PDU{dap-ip}

dap-ip IDM-PROTOCOL ::= {
  BIND-OPERATION  directoryBind
  OPERATIONS
    {read | compare | abandon | list | search | addEntry | removeEntry |
      modifyEntry | modifyDN}
  ID              id-idm-dap
}

DSP-IDM-PDUs ::= IDM-PDU{dsp-ip}

dsp-ip IDM-PROTOCOL ::= {
  BIND-OPERATION  dSABind
  OPERATIONS
    {chainedRead | chainedCompare | chainedAbandon | chainedList |
      chainedSearch | chainedAddEntry | chainedRemoveEntry | chainedModifyEntry
      | chainedModifyDN}
  ID              id-idm-dsp
}

DISP-IDM-PDUs ::= IDM-PDU{disp-ip}

disp-ip IDM-PROTOCOL ::= {
  BIND-OPERATION  dSAShadowBind
  OPERATIONS      {requestShadowUpdate | updateShadow | coordinateShadowUpdate}
  ID              id-idm-disp
}

DOP-IDM-PDUs ::= IDM-PDU{dop-ip}

dop-ip IDM-PROTOCOL ::= {
  BIND-OPERATION  dSAOperationalBindingManagementBind
  OPERATIONS
    {establishOperationalBinding | modifyOperationalBinding |
      terminateOperationalBinding}
  ID              id-idm-dop
}

-- protocol object identifiers 
id-idm-dap OBJECT IDENTIFIER ::= {id-idm 0}

id-idm-dsp OBJECT IDENTIFIER ::= {id-idm 1}

id-idm-disp OBJECT IDENTIFIER ::= {id-idm 2}

id-idm-dop OBJECT IDENTIFIER ::= {id-idm 3}

END -- DirectoryIDMProtocols

-- Generated by Asnp, the ASN.1 pretty-printer of France Telecom R&D

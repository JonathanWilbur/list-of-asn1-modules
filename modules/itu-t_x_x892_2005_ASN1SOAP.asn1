ASN1SOAP (X.892:05/2005)


-- Module ASN1SOAP (X.892:05/2005)
-- See also ITU-T X.892 (05/2005)
-- See also the index of all ASN.1 assignments needed in this document

ASN1SOAP {joint-iso-itu-t(2) asn1(1) generic-applications(10)
  fast-web-services(1) modules(0) asn1soap(0)} DEFINITIONS AUTOMATIC TAGS ::=
BEGIN

IMPORTS
  AnyURI, Int, Language, QName
    FROM XSD {joint-iso-itu-t asn1(1) specification(0) modules(0) xsd-module(2)
      }
  Document, finf-doc-no-decl
    FROM FastInfoset {joint-iso-itu-t(2) asn1(1) generic-applications(10)
      fast-infoset(0) modules(0) fast-infoset(0)};

Envelope ::= SEQUENCE {
  header         Header,
  body-or-fault  CHOICE {body   Body,
                         fault  Fault}
}

Header ::= SEQUENCE OF HeaderBlock

HeaderBlock ::= SEQUENCE {
  mustUnderstand  BOOLEAN OPTIONAL,
  relay           BOOLEAN OPTIONAL,
  role            XSD.AnyURI DEFAULT ultimateReceiver,
  content         Content
}

ultimateReceiver XSD.AnyURI ::=
  "http://www.w3.org/2003/05/soap-envelope/role/UltimateReceiver"

Body ::= SEQUENCE {content  Content OPTIONAL
}

Fault ::= SEQUENCE {
  code    Code,
  reason  SEQUENCE SIZE (1..MAX) OF Text,
  node    XSD.AnyURI OPTIONAL,
  role    XSD.AnyURI OPTIONAL,
  detail  Content OPTIONAL
}

Code ::= SEQUENCE {value     Value,
                   subcodes  SEQUENCE OF XSD.QName
}

Value ::= ENUMERATED {
  versionMismatch, mustUnderstand, dataEncodingUnknown, sender, receiver
}

Text ::= SEQUENCE {lang  XSD.Language,
                   text  UTF8String
}

Content ::= CHOICE {
  encoded-value
    SEQUENCE {schema-identifier  OCTET STRING(SIZE (16)) OPTIONAL,
              id                 Identifier,
              encoding           OCTET STRING},
  fast-infoset-document
    OCTET STRING(CONTAINING Document ENCODED BY finf-doc-no-decl)
}

Identifier ::= CHOICE {roid   RELATIVE-OID,
                       qName  XSD.QName
}

NotUnderstood ::= XSD.QName

notUnderstoodIdentifier Identifier ::=
  qName:{uri "http://www/w3/org/2003/05/soap-envelope", name "NotUnderstood"}

END

-- Generated by Asnp, the ASN.1 pretty-printer of France Telecom R&D

SMASE-A-ASSOCIATE-Information (Rec. X.701:08/1997)


-- Module SMASE-A-ASSOCIATE-Information (X.701:08/1997)-- See also ITU-T X.701 (08/1997)-- See also the index of all ASN.1 assignments needed in this Recommendation

SMASE-A-ASSOCIATE-Information {joint-iso-itu-t ms(9) smo(0) asn1Modules(2)
  negotiationDefinitions(0) version1(1)} DEFINITIONS ::=
BEGIN

SMASEUserData ::= SEQUENCE {
  smfuPackages                      SET OF FunctionalUnitPackage OPTIONAL,
  -- shall be present on request/indication if SMFU 
  -- negotiation is proposed and on response/confirm
  -- if SMFU negotiation is accepted, otherwise this
  -- parameter shall be omitted.
  reason                            Reason OPTIONAL,
  -- may only be present on A-ASSOCIATE response/confirm.
  -- When SMFU negotiation fails, when SMFU negotiation 
  -- results in a reduction of the proposed set of SMFUs
  -- or when the association request is rejected, it may 
  -- carry a specific reason for this.
  systemsManagementUserInformation  GraphicString OPTIONAL
  -- this parameter is provided solely for the convenience
  -- of implementations needing to distinguish between 
  -- different implementation environments, it shall not
  -- be the subject of conformance test
}

Reason ::= INTEGER {
  smfusNotSupported(0),
  -- one or more of the requested SMFUs are not supported
  smfuCombinationNotSupported(1),
  -- the individual SMFUs are supported, but not
  -- in this proposed combination on a single association
  smfusRequiredNotAvailable(2),
  -- one or more required SMFUs have been negotiated away
  smfuNegotiationRefused(3)
  -- responder refuses to negotiate SMFUs
  -- without explicitly stating why
  }

FunctionalUnitPackage ::= SEQUENCE {
  functionalUnitPackageId    FunctionalUnitPackageId,
  managerRoleFunctionalUnit  [0] IMPLICIT BIT STRING DEFAULT {},
  -- If not present implies role not supported for this functionalUnitPackage.
  agentRoleFunctionalUnit    [1] IMPLICIT BIT STRING DEFAULT {}
  -- If not present implies role not supported for this functionalUnitPackage.
}

FunctionalUnitPackageId ::= OBJECT IDENTIFIER

END

-- Generated by Asnp, the ASN.1 pretty-printer of France Telecom R&amp;D

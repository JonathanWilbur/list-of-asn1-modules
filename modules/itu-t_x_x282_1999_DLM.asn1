DLM (X.282:06/1999)


-- Module DLM (X.282:06/1999)
-- See also ITU-T X.282 (06/1999)
-- See also the index of all ASN.1 assignments needed in this document

DLM {joint-iso-itu-t datalink-layer(15) management(0) asn1Module(2) 0}
DEFINITIONS IMPLICIT TAGS ::=
BEGIN

IMPORTS
  GroupObjects, ObservedValue, PerceivedSeverity
    FROM Attribute-ASN1Module {joint-iso-itu-t ms(9) smi(3) part2(2)
      asn1Module(2) 1}
  SetInfoStatus, AttributeId, ObjectInstance
    FROM CMIP-1 {joint-iso-itu-t ms(9) cmip(1) modules(0) protocol(3)};

--  "infrastructure" object identifier definitions
datalink-layer OBJECT IDENTIFIER ::=
  {joint-iso-itu-t datalink-layer(15)}

dloi OBJECT IDENTIFIER ::= {datalink-layer management(0)}

sseoi OBJECT IDENTIFIER ::= {dloi standardSpecificExtension(0)}

moi OBJECT IDENTIFIER ::= {dloi objectClass(3)}

poi OBJECT IDENTIFIER ::= {dloi package(4)}

proi OBJECT IDENTIFIER ::= {dloi parameter(5)}

nboi OBJECT IDENTIFIER ::= {dloi nameBinding(6)}

aoi OBJECT IDENTIFIER ::= {dloi attribute(7)}

agoi OBJECT IDENTIFIER ::= {dloi attributeGroup(8)}

acoi OBJECT IDENTIFIER ::= {dloi action(9)}

noi OBJECT IDENTIFIER ::= {dloi notification(10)}

k OBJECT IDENTIFIER ::= {aoi 19}

n1 OBJECT IDENTIFIER ::= {aoi 20}

n2 OBJECT IDENTIFIER ::= {aoi 21}

sequenceModulus OBJECT IDENTIFIER ::= {aoi 24}

t1Timer OBJECT IDENTIFIER ::= {aoi 25}

t2Timer OBJECT IDENTIFIER ::= {aoi 26}

t3Timer OBJECT IDENTIFIER ::= {aoi 27}

t4Timer OBJECT IDENTIFIER ::= {aoi 28}

--
--  value assignments for Data Link layer specificProblems
--
fRMRReceived OBJECT IDENTIFIER ::=
  {sseoi specificProblems(11) fRMRReceived(5)}

fRMRReasons OBJECT IDENTIFIER ::= {sseoi specificProblems(11) fRMRReasons(6)}

fRMRReasonsControlFieldUndefinedOrUnimplemented OBJECT IDENTIFIER ::=
  {sseoi specificProblems(11) fRMRReasons(6)
   controlFieldUndefinedOrUnimplemented(1)}

fRMRReasonsFormatError OBJECT IDENTIFIER ::=
  {sseoi specificProblems(11) fRMRReasons(6) formatError(2)}

fRMRReasonsInfoFieldLengthGreaterThanMaximum OBJECT IDENTIFIER ::=
  {sseoi specificProblems(11) fRMRReasons(6)
   infoFieldLengthGreaterThanMaximum(3)}

fRMRReasonsInvalidNR OBJECT IDENTIFIER ::=
  {sseoi specificProblems(11) fRMRReasons(6) invalidNR(4)}

fRMRReasonsNonSpecific OBJECT IDENTIFIER ::=
  {sseoi specificProblems(11) fRMRReasons(6) nonSpecific(5)}

--
--  value assignments for Data Link layer specific errorIds for activate action processingFailure
--  errors.
--
activateFailure OBJECT IDENTIFIER ::=
  {sseoi action(9) activate(1) errors(1) processingFailure(1)}

activateFailureInsufficientResources OBJECT IDENTIFIER ::=
  {activateFailure insufficientResources(1)}

activateFailureProviderDoesNotExist OBJECT IDENTIFIER ::=
  {activateFailure providerDoesNotExist(2)}

activateFailureProviderNotAvailable OBJECT IDENTIFIER ::=
  {activateFailure providerNotAvailable(3)}

activateFailureRequiredServiceNotAvailable OBJECT IDENTIFIER ::=
  {activateFailure requiredServiceNotAvailable(4)}

activateFailureSystemSpecific OBJECT IDENTIFIER ::=
  {activateFailure systemSpecific(5)}

--
--  other definitions
--
datalinkSubsystemId-Value GraphicString ::=
  "datalinkSubsystem"

FRMRSyntax ::= OCTET STRING

NamingString ::= GraphicString

Integer ::= INTEGER

InterfaceType ::= ENUMERATED {dTE(0), dCE(1)}

interfaceTypeDefault InterfaceType ::= dTE

MaximumIFrameSize ::= INTEGER

--  in bits, 1080 (135 octets) minimum
MW ::= SEQUENCE {
  mWSend     [0] IMPLICIT INTEGER(0..4095),
  mWReceive  [1] IMPLICIT INTEGER(0..4095)
}

MX ::= SEQUENCE {
  mXSend     [0] IMPLICIT INTEGER(0..4095),
  mXReceive  [1] IMPLICIT INTEGER(0..4095)
}

Octet ::= OCTET STRING(SIZE (1))

OctetString ::= OCTET STRING

SequenceModulus ::= Integer

SLPProtocolState ::= ENUMERATED {
  disconnectedPhase(0), linkdisconnection-phase(1), link-set-up-phase(2),
  information-Transfer-phase(3), frame-Reject-condition(4), busy-condition(5),
  sent-Reject-condition(6), system-Parameters-and-error-recovery(7)}

WindowSize ::= CHOICE {
  modulo8ws    [0]  INTEGER(1..7), --  for modulo 8
  modulo128ws  [1]  INTEGER(1..127)
} --  for modulo 128

END

-- Generated by Asnp, the ASN.1 pretty-printer of France Telecom R&D

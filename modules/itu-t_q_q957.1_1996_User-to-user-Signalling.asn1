User-to-user-Signalling (Q.957.1:07/1996)


-- Module User-to-user-Signalling (Q.957.1:07/1996)
-- See also ITU-T Q.957.1 (07/1996)
-- See also the index of all ASN.1 assignments needed in this document

User-to-user-Signalling {itu-t(0) recommendation(0) q(17) q957(957) part1(1)
  operations-and-errors(1)} DEFINITIONS ::=
BEGIN

EXPORTS userUserService;

IMPORTS
  OPERATION, ERROR
    --FROM Remote-Operation-Notation {joint-iso-itu-t remote-operations (4) notations}
    FROM Remote-Operations-Information-Objects {joint-iso-itu-t
      remote-operations(4) informationObjects(5) version1(0)}
  rejectedByNetwork, rejectedByUser
    FROM General-Error-List {itu-t recommendation q 950 general-error-list(1)};

userUserService OPERATION ::= {
  ARGUMENT
    SEQUENCE {service    [1] IMPLICIT Service,
              preferred  [2] IMPLICIT Preferred}
  ERRORS    {rejectedByNetwork | rejectedByUser}
  CODE      local:1
}

uUSRequest OPERATION ::= {
  ARGUMENT
    SEQUENCE {service    [1] IMPLICIT Service,
              preferred  [2] IMPLICIT Preferred}
  CODE      local:66
}

Service ::= INTEGER {service1(1), service2(2), service3(3)}(1..3)

Preferred ::= BOOLEAN

preferred Preferred ::= TRUE

required Preferred ::= FALSE

END

-- Generated by Asnp, the ASN.1 pretty-printer of France Telecom R&D

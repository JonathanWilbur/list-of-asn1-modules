CommonMgt (ISO/IEC 10589:2002)


-- Module CommonMgt (ISO/IEC 10589:2002)
-- See also
ITU-T 
formal description search tool
-- See also the index of all ASN.1 assignments needed in this Standard

--
-- Copyright © ISO/IEC 1991. This version of
-- this ASN.1 module is part of ISO/IEC 10589:2002;
-- see the ISO|IEC text itself for full legal notices.
-- 
CommonMgt {joint-iso-ccitt network-layer(13) management(0) sc6-gmi(0)
  asn1Module(2) 0} DEFINITIONS IMPLICIT TAGS ::=
BEGIN

-- EXPORTS everything
IMPORTS
  BaseManagedObjectId
    FROM CMIP-1 {joint-iso-itu-t ms(9) cmip(1) modules(0) protocol(3)};

-- "infrastructure" object identifier definitions
cmoi OBJECT IDENTIFIER ::=
  {joint-iso-ccitt network-layer(13) management(0) sc6-gmi(0)}

sseoi OBJECT IDENTIFIER ::= {cmoi standardSpecificExtensions(0)}

fupoi OBJECT IDENTIFIER ::= {cmoi functionalUnitPackage(1)}

moi OBJECT IDENTIFIER ::= {cmoi managedObjectClass(3)}

poi OBJECT IDENTIFIER ::= {cmoi package(4)}

proi OBJECT IDENTIFIER ::= {cmoi parameter(5)}

aoi OBJECT IDENTIFIER ::= {cmoi attribute(7)}

agoi OBJECT IDENTIFIER ::= {cmoi attributeGroup(8)}

acoi OBJECT IDENTIFIER ::= {cmoi action(9)}

noi OBJECT IDENTIFIER ::= {cmoi notification(10)}

-- other definitions
ActionInfo ::= SET OF Parameter

ActionReply ::= SEQUENCE {
  responseCode  OBJECT IDENTIFIER,
  responseArgs  SET OF Parameter OPTIONAL
}

counterInitialValue NonWrappingCounter ::= 0

InformationData ::= SET OF Parameter

CommunicationsInformation ::= SEQUENCE {
  informationType  InformationType,
  informationData  InformationData OPTIONAL
}

InformationType ::= OBJECT IDENTIFIER

CommunicationsEntityId ::= GraphicString

ConnectionId ::= GraphicString

failureResponse OBJECT IDENTIFIER ::= {responseCode failureResponse(1001)}

informationEventReports OBJECT IDENTIFIER ::=
  {fupoi informationEventReports(1000)}

NonWrappingCounter ::= INTEGER(0..18446744073709551615) -- (0..2^64-1)
                              

NotificationInfo ::= SET OF Parameter

PARAMETER ::= CLASS {&amp;id    OBJECT IDENTIFIER UNIQUE,
                     &amp;Type  
}WITH SYNTAX {PARAMETER &amp;id
              INFO &amp;Type
}

Parameter ::= SEQUENCE {
  paramId    PARAMETER.&amp;id({Parameters}),
  paramInfo  PARAMETER.&amp;Type({Parameters}{@paramId})
}

Parameters PARAMETER ::=
  {...} -- dynamically extensible object set

ProtocolMachineId ::= GraphicString

ProviderObjects ::= SET OF BaseManagedObjectId

-- only the localDistinguishedName form of ObjectInstance is used
responseCode OBJECT IDENTIFIER ::=
  {proi responseCode(1001)}

-- value assignments for specific action response codes are registered
-- under this OID.
ResponseCode ::= OBJECT IDENTIFIER

Sap1Address ::= INTEGER

Sap2Addresses ::= SET OF OCTET STRING

SapId ::= GraphicString

SubsystemId ::= GraphicString

successResponse OBJECT IDENTIFIER ::= {responseCode successResponse(1002)}

--Timer ::= SEQUENCE {
--exponent [1] INTEGER(-62..63),
--mantissa [2] INTEGER(0..65535)}
UserObjects ::= SET OF BaseManagedObjectId

-- only the localDistinguishedName form of ObjectInstance is used
END

-- Generated by Asnp, the ASN.1 pretty-printer of France Telecom R&amp;D

EXAMPLES (X.694:01/2004)


-- Module EXAMPLES (X.694:01/2004)
-- See also ITU-T X.694 (01/2004)
-- See also the index of all ASN.1 assignments needed in this document

EXAMPLES 
DEFINITIONS AUTOMATIC TAGS XER INSTRUCTIONS ::=
BEGIN

IMPORTS
  String, Decimal, Int, Date, AnyType
    FROM XSD {joint-iso-itu-t asn1(1) specification(0) modules(0) xsd-module(2)
      version1(1)};

EXAMPLES ::= SEQUENCE {
  personnelRecord       PersonnelRecord,
  number                Decimal,
  daysOfTheWeek         ListOfDays,
  namesOfMemberNations  NamesOfMemberNations,
  fileIdentifier-list
     [UNTAGGED] SEQUENCE (SIZE (1..MAX)) OF fileidentifier FileIdentifier
}

PersonnelRecord ::= SEQUENCE {
  name          Name,
  title         XSD.String,
  number        INTEGER,
  dateOfHire    Date,
  nameOfSpouse  NameOfSpouse,
  children      Children
}

NameOfSpouse ::= [NAME AS UNCAPITALIZED] Name

Name ::= [NAME AS UNCAPITALIZED] SEQUENCE {
  givenName   XSD.String,
  initial     XSD.String,
  familyName  XSD.String
}

Children ::= [NAME AS UNCAPITALIZED] SEQUENCE {
  childInformation-list   [UNTAGGED] SEQUENCE OF ChildInformation
}

ChildInformation ::= SEQUENCE {name         Name,
                               dateOfBirth  Date
}

ListOfDays ::= [LIST] SEQUENCE OF Day

Day ::= ENUMERATED {
  monday, tuesday, wednesday, thursday, friday, saturday, sunday}

NamesOfMemberNations ::= [NAME AS UNCAPITALIZED] [LIST] SEQUENCE OF XSD.String

FileIdentifier ::= SEQUENCE {
  choice
    [UNTAGGED] CHOICE {serialNumber  Int,
                           relativeName  XSD.String,
                           unidentified  UNIDENTIFIED}
}

UNIDENTIFIED ::= [NAME AS LOWERCASED] XSD.AnyType

ENCODING-CONTROL XER
GLOBAL-DEFAULTS MODIFIED-ENCODINGS
END

-- Generated by Asnp, the ASN.1 pretty-printer of France Telecom R&D

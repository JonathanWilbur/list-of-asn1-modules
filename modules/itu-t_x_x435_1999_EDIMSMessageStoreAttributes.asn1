EDIMSMessageStoreAttributes (X.435:06/1999)


-- Module EDIMSMessageStoreAttributes (X.435:06/1999)
-- See also ITU-T X.435 (06/1999)
-- See also the index of all ASN.1 assignments needed in this document

EDIMSMessageStoreAttributes {joint-iso-itu-t mhs(6) edims(7) modules(0)
  message-store-attributes(4) version(2)} DEFINITIONS IMPLICIT TAGS ::=
BEGIN

--	Prologue
--	Exports everything
IMPORTS
  --	EDIMS Object Identifiers
  id-bat-body, id-bat-edi-body-part, id-bat-edim-body-part,
    id-bat-extended-body-part-types, id-bat-interchange-length,
    id-bat-message-data, id-bat-message-parameters,
    id-cat-correlated-delivered-edins, id-cat-delivered-edin-summary,
    id-cat-edim-recipients, id-cat-forwarded-edims, id-cat-forwarding-edims,
    id-cat-obsoleted-edims, id-cat-obsoleting-edims, id-cat-related-edims,
    id-cat-relating-edims, id-cat-subject-edim, id-cat-submitted-edin-status,
    id-cat-submitted-edins, id-hat-application-reference,
    id-hat-cross-referencing-information, id-hat-date-and-time-of-preparation,
    id-hat-edi-application-security-element,
    id-hat-edi-application-security-extensions, id-hat-edi-bodypart-type,
    id-hat-edi-message-type, id-hat-edin-receiver, id-hat-expiry-time,
    id-hat-heading, id-hat-heading-extensions, id-hat-incomplete-copy,
    id-hat-interchange-sender, id-hat-obsoleted-edims, id-hat-originator,
    id-hat-recipients, id-hat-related-messages,
    id-hat-responsibility-forwarded, id-hat-service-string-advice,
    id-hat-syntax-identifier, id-hat-this-edim, id-nat-edin-initiator,
    id-nat-edin-originator, id-nat-first-recipient, id-nat-fn-extensions,
    id-nat-fn-reason-code, id-nat-fn-supplementary-info, id-nat-forwarded-to,
    id-nat-nn-extensions, id-nat-nn-reason-code, id-nat-nn-supplementary-info,
    id-nat-notification-extensions, id-nat-notification-security-elements,
    id-nat-notification-time, id-nat-pn-extensions,
    id-nat-pn-supplementary-info, id-nat-subject-edim,
    id-rat-acknowledgement-request-for-this-recipient,
    id-rat-action-request-for-this-recipient,
    id-rat-authorization-information-for-this-recipient,
    id-rat-communications-agreement-id-for-this-recipient,
    id-rat-edi-notification-requests-for-this-recipient,
    id-rat-edi-notification-security-for-this-recipient,
    id-rat-edi-reception-security-for-this-recipient,
    id-rat-interchange-control-reference-for-this-recipient,
    id-rat-interchange-recipient-for-this-recipient,
    id-rat-processing-priority-code-for-this-recipient,
    id-rat-recipient-extensions-for-this-recipient, id-rat-this-recipient,
    id-rat-recipient-reference-for-this-recipient,
    id-rat-responsibility-passing-allowed-for-this-recipient,
    id-rat-test-indicator-for-this-recipient,
    id-sat-edi-notification-indicator, id-sat-edim-synopsis,
    id-sat-edims-entry-type
    --==
    FROM EDIMSObjectIdentifiers {joint-iso-itu-t mhs(6) edims(7) modules(0)
      object-identifiers(0) version(2)}
  --	EDIMS Information Objects
  AcknowledgementRequestField, ActionRequestField, ApplicationReferenceField,
    AuthorizationInformationField, Body, BodyPartReference,
    CommunicationsAgreementIdField, CrossReferencingInformationSubField,
    DateAndTimeOfPreparationField, EDIApplicationSecurityElement,
    EDIApplicationSecurityExtension, EDIBodyPart, EDIBodyPartType,
    EDIMessageTypeFieldSubField, EDINInitiatorField, EDINOriginatorField,
    EDINotificationRequests, EDINotificationSecurity, EDINReceiverField,
    EDIReceptionSecurity, EDISupplementaryInformation, ExpiryTimeField,
    FirstRecipientField, FNExtensionsSubField, FNReasonCodeField, ForwardedTo,
    Heading, HeadingExtensionsSubField, IncompleteCopyField,
    InterchangeControlReferenceField, InterchangeRecipientField,
    InterchangeSenderField, MessageData, MessageParameters, NNReasonCodeField,
    NNExtensionsSubField, NotificationExtensionsSubField,
    NotificationTimeField, ObsoletedEDIMsSubfield, OriginatorField,
    PositiveNotificationFields, PNExtensionsSubField,
    ProcessingPriorityCodeField, RecipientExtensionsSubField, RecipientField,
    RecipientReferenceField, RecipientsSubField, RelatedMessageReference,
    ResponsibilityForwarded, ResponsibilityPassingAllowedField,
    SecurityElementsField, ServiceStringAdviceField, SubjectEDIMField,
    SyntaxIdentifierField, TestIndicatorField, ThisEDIMField
    --==
    FROM EDIMSInformationObjects {joint-iso-itu-t mhs(6) edims(7) modules(0)
      information-objects(2) version(2)}
  --	MS Abstract Service
  X413ATTRIBUTE, SequenceNumber
    --==
    FROM MSAbstractService {joint-iso-itu-t mhs(6) ms(4) modules(0)
      abstract-service(1) version-1999(1)}
  --	MS Matching-rules
  mSStringMatch, mSSubstringsMatch, oRNameElementsMatch, oRNameMatch,
    oRNameSingleElementMatch, oRNameSubstringElementsMatch
    --==
    FROM MSMatchingRules {joint-iso-itu-t mhs(6) ms(4) modules(0)
      general-matching-rules(5) version-1999(1)}
  --	IPMS Matching-rules
  iPMIdentifierMatch, iPMLocationMatch
    --==
    FROM IPMSMessageStoreAttributes {joint-iso-itu-t mhs(6) ipms(1) modules(0)
      message-store-attributes(8) version-1999(1)}
  --	Directory matching-rules
  bitStringMatch, booleanMatch, integerMatch, integerOrderingMatch,
    uTCTimeMatch, uTCTimeOrderingMatch
    --==
    FROM SelectedAttributeTypes {joint-iso-itu-t ds(5) module(1)
      selectedAttributeTypes(5) 3}
  objectIdentifierMatch
    --==
    FROM InformationFramework {joint-iso-itu-t ds(5) module(1)
      informationFramework(1) 3}
  --	IPMS Information Objects
  EXTENDED-BODY-PART-TYPE
    --==
    FROM IPMSInformationObjects {joint-iso-itu-t mhs(6) ipms(1) modules(0)
      information-objects(2) version-1999(1)}
  --	MTS Abstract Service
  ORName
    --==
    FROM MTSAbstractService {joint-iso-itu-t mhs(6) mts(3) modules(0)
      mts-abstract-service(1) version-1999(1)};

--	END imports
--	MESSAGE STORE ATTRIBUTES
--	Summary Attributes
--	EDIMS Entry Type
edims-entry-type X413ATTRIBUTE ::= {
  WITH ATTRIBUTE-SYNTAX   EDIMSEntryType,
  EQUALITY MATCHING-RULE  integerMatch,
  NUMERATION              single-valued,
  ID                      id-sat-edims-entry-type
}

EDIMSEntryType ::= ENUMERATED {edim(0), pn(1), nn(2), fn(3)}

--	EDIM Synopsis
edim-synopsis X413ATTRIBUTE ::= {
  WITH ATTRIBUTE-SYNTAX  EDIMSynopsis,
  NUMERATION             single-valued,
  ID                     id-sat-edim-synopsis
}

EDIMSynopsis ::= SEQUENCE OF BodyPartSynopsis

BodyPartSynopsis ::= CHOICE {
  message      [0]  MessageBodyPartSynopsis,
  non-message  [1]  NonMessageBodyPartSynopsis
}

MessageBodyPartSynopsis ::= SEQUENCE {
  number    [0]  SequenceNumber,
  synopsis  [1]  EDIMSynopsis
}

NonMessageBodyPartSynopsis ::= SEQUENCE {
  type        [0]  OBJECT IDENTIFIER,
  parameters  [1]  INSTANCE OF TYPE-IDENTIFIER OPTIONAL,
  size        [2]  INTEGER,
  processed   [3]  BOOLEAN DEFAULT FALSE
}

--	EDI Notification Indicator
edi-notification-indicator X413ATTRIBUTE ::= {
  WITH ATTRIBUTE-SYNTAX   EDINotificationIndicator,
  EQUALITY MATCHING-RULE  integerMatch,
  NUMERATION              single-valued,
  ID                      id-sat-edi-notification-indicator
}

EDINotificationIndicator ::= ENUMERATED {
  no-notification-sent(0), pn-sent(1), nn-sent(2), fn-sent(3)}

--	Heading Attributes
--	Heading
heading X413ATTRIBUTE ::= {
  WITH ATTRIBUTE-SYNTAX  Heading,
  NUMERATION             single-valued,
  ID                     id-hat-heading
}

--	Heading Fields
this-edim X413ATTRIBUTE ::= {
  WITH ATTRIBUTE-SYNTAX   ThisEDIMField,
  EQUALITY MATCHING-RULE  iPMIdentifierMatch,
  NUMERATION              single-valued,
  ID                      id-hat-this-edim
}

originator X413ATTRIBUTE ::= {
  WITH ATTRIBUTE-SYNTAX   OriginatorField,
  EQUALITY MATCHING-RULE  oRNameMatch,
  NUMERATION              single-valued,
  ID                      id-hat-originator
}

edin-receiver X413ATTRIBUTE ::= {
  WITH ATTRIBUTE-SYNTAX  EDINReceiverField,
                           
  -- EQUALITY MATCHING-RULE   rule not defined 
  NUMERATION             single-valued,
  ID                     id-hat-edin-receiver
}

responsibility-forwarded X413ATTRIBUTE ::= {
  WITH ATTRIBUTE-SYNTAX   ResponsibilityForwarded,
  EQUALITY MATCHING-RULE  booleanMatch,
  NUMERATION              single-valued,
  ID                      id-hat-responsibility-forwarded
}

edi-bodypart-type X413ATTRIBUTE ::= {
  WITH ATTRIBUTE-SYNTAX   EDIBodyPartType,
  EQUALITY MATCHING-RULE  objectIdentifierMatch,
  NUMERATION              single-valued,
  ID                      id-hat-edi-bodypart-type
}

incomplete-copy X413ATTRIBUTE ::= {
  WITH ATTRIBUTE-SYNTAX   IncompleteCopyField,
  EQUALITY MATCHING-RULE  booleanMatch,
  NUMERATION              single-valued,
  ID                      id-hat-incomplete-copy
}

expiry-time X413ATTRIBUTE ::= {
  WITH ATTRIBUTE-SYNTAX   ExpiryTimeField,
  EQUALITY MATCHING-RULE  uTCTimeMatch,
  ORDERING MATCHING-RULE  uTCTimeOrderingMatch, -- not defined in version 1 
                            
  NUMERATION              single-valued,
  ID                      id-hat-expiry-time
}

related-messages X413ATTRIBUTE ::= {
  WITH ATTRIBUTE-SYNTAX  RelatedMessageReference,
                           
  -- EQUALITY MATCHING-RULE   rule not defined 
  NUMERATION             multi-valued,
  ID                     id-hat-related-messages
}

obsoleted-edims X413ATTRIBUTE ::= {
  WITH ATTRIBUTE-SYNTAX   ObsoletedEDIMsSubfield,
  EQUALITY MATCHING-RULE  iPMIdentifierMatch,
  NUMERATION              multi-valued,
  ID                      id-hat-obsoleted-edims
}

edi-application-security-element X413ATTRIBUTE ::= {
  WITH ATTRIBUTE-SYNTAX   EDIApplicationSecurityElement,
  EQUALITY MATCHING-RULE  bitStringMatch,
  NUMERATION              single-valued,
  ID                      id-hat-edi-application-security-element
}

edi-application-security-extensions X413ATTRIBUTE ::= {
  WITH ATTRIBUTE-SYNTAX   EDIApplicationSecurityExtension,
  EQUALITY MATCHING-RULE  bitStringMatch,
  NUMERATION              multi-valued,
  ID                      id-hat-edi-application-security-extensions
}

cross-referencing-information X413ATTRIBUTE ::= {
  WITH ATTRIBUTE-SYNTAX   CrossReferencingInformationSubField,
  EQUALITY MATCHING-RULE  bitStringMatch,
  NUMERATION              multi-valued,
  ID                      id-hat-cross-referencing-information
}

--	Fields from EDIFACT Interchange:
edi-message-type X413ATTRIBUTE ::= {
  WITH ATTRIBUTE-SYNTAX   EDIMessageTypeFieldSubField,
  EQUALITY MATCHING-RULE  mSStringMatch,
  NUMERATION              multi-valued,
  ID                      id-hat-edi-message-type
}

service-string-advice X413ATTRIBUTE ::= {
  WITH ATTRIBUTE-SYNTAX  ServiceStringAdviceField,
                           
  -- EQUALITY MATCHING-RULE   rule not defined 
  NUMERATION             single-valued,
  ID                     id-hat-service-string-advice
}

syntax-identifier X413ATTRIBUTE ::= {
  WITH ATTRIBUTE-SYNTAX  SyntaxIdentifierField,
                           
  -- EQUALITY MATCHING-RULE   rule not defined 
  NUMERATION             single-valued,
  ID                     id-hat-syntax-identifier
}

interchange-sender X413ATTRIBUTE ::= {
  WITH ATTRIBUTE-SYNTAX  InterchangeSenderField,
                           
  -- EQUALITY MATCHING-RULE   rule not defined 
  NUMERATION             single-valued,
  ID                     id-hat-interchange-sender
}

date-and-time-of-preparation X413ATTRIBUTE ::= {
  WITH ATTRIBUTE-SYNTAX   DateAndTimeOfPreparationField,
  EQUALITY MATCHING-RULE  uTCTimeMatch,
  ORDERING MATCHING-RULE
    uTCTimeOrderingMatch, -- rule not defined in version 1 
      
  NUMERATION              single-valued,
  ID                      id-hat-date-and-time-of-preparation
}

application-reference X413ATTRIBUTE ::= {
  WITH ATTRIBUTE-SYNTAX     ApplicationReferenceField,
  EQUALITY MATCHING-RULE    mSStringMatch,
  SUBSTRINGS MATCHING-RULE  mSSubstringsMatch,
  NUMERATION                single-valued,
  ID                        id-hat-application-reference
}

--	Heading extensions:
heading-extensions X413ATTRIBUTE ::= {
  WITH ATTRIBUTE-SYNTAX  HeadingExtensionsSubField,
                           
  -- EQUALITY MATCHING-RULE   rule not defined 
  NUMERATION             multi-valued,
  ID                     id-hat-heading-extensions
}

--	Recipient Subfield
this-recipient X413ATTRIBUTE ::= {
  WITH ATTRIBUTE-SYNTAX   RecipientField,
  EQUALITY MATCHING-RULE  oRNameMatch,
  NUMERATION              single-valued,
  ID                      id-rat-this-recipient
}

action-request-for-this-recipient X413ATTRIBUTE ::= {
  WITH ATTRIBUTE-SYNTAX   ActionRequestField,
  EQUALITY MATCHING-RULE  objectIdentifierMatch,
  NUMERATION              single-valued,
  ID                      id-rat-action-request-for-this-recipient
}

edi-notification-requests-for-this-recipient X413ATTRIBUTE ::= {
  WITH ATTRIBUTE-SYNTAX   EDINotificationRequests,
  EQUALITY MATCHING-RULE  bitStringMatch,
  NUMERATION              single-valued,
  ID                      id-rat-edi-notification-requests-for-this-recipient
}

edi-notification-security-for-this-recipient X413ATTRIBUTE ::= {
  WITH ATTRIBUTE-SYNTAX   EDINotificationSecurity,
  EQUALITY MATCHING-RULE  bitStringMatch,
  NUMERATION              single-valued,
  ID                      id-rat-edi-notification-security-for-this-recipient
}

edi-reception-security-for-this-recipient X413ATTRIBUTE ::= {
  WITH ATTRIBUTE-SYNTAX   EDIReceptionSecurity,
  EQUALITY MATCHING-RULE  bitStringMatch,
  NUMERATION              single-valued,
  ID                      id-rat-edi-reception-security-for-this-recipient
}

responsibility-passing-allowed-for-this-recipient X413ATTRIBUTE ::= {
  WITH ATTRIBUTE-SYNTAX   ResponsibilityPassingAllowedField,
  EQUALITY MATCHING-RULE  booleanMatch,
  NUMERATION              single-valued,
  ID
    id-rat-responsibility-passing-allowed-for-this-recipient
}

--	Fields from EDIFACT interchange
interchange-recipient-for-this-recipient X413ATTRIBUTE ::= {
  WITH ATTRIBUTE-SYNTAX  InterchangeRecipientField,
                           
  -- EQUALITY MATCHING-RULE   rule not defined 
  NUMERATION             single-valued,
  ID                     id-rat-interchange-recipient-for-this-recipient
}

recipient-reference-for-this-recipient X413ATTRIBUTE ::= {
  WITH ATTRIBUTE-SYNTAX  RecipientReferenceField,
                           
  -- EQUALITY MATCHING-RULE   rule not defined 
  NUMERATION             single-valued,
  ID                     id-rat-recipient-reference-for-this-recipient
}

interchange-control-reference-for-this-recipient X413ATTRIBUTE ::= {
  WITH ATTRIBUTE-SYNTAX     InterchangeControlReferenceField,
  EQUALITY MATCHING-RULE    mSStringMatch,
  SUBSTRINGS MATCHING-RULE  mSSubstringsMatch,
  NUMERATION                single-valued,
  ID
    id-rat-interchange-control-reference-for-this-recipient
}

processing-priority-code-for-this-recipient X413ATTRIBUTE ::= {
  WITH ATTRIBUTE-SYNTAX   ProcessingPriorityCodeField,
  EQUALITY MATCHING-RULE  mSStringMatch,
  NUMERATION              single-valued,
  ID                      id-rat-processing-priority-code-for-this-recipient
}

acknowledgement-request-for-this-recipient X413ATTRIBUTE ::= {
  WITH ATTRIBUTE-SYNTAX   AcknowledgementRequestField,
  EQUALITY MATCHING-RULE  booleanMatch,
  NUMERATION              single-valued,
  ID                      id-rat-acknowledgement-request-for-this-recipient
}

communications-agreement-id-for-this-recipient X413ATTRIBUTE ::= {
  WITH ATTRIBUTE-SYNTAX     CommunicationsAgreementIdField,
  EQUALITY MATCHING-RULE    mSStringMatch,
  SUBSTRINGS MATCHING-RULE  mSSubstringsMatch,
  NUMERATION                single-valued,
  ID
    id-rat-communications-agreement-id-for-this-recipient
}

test-indicator-for-this-recipient X413ATTRIBUTE ::= {
  WITH ATTRIBUTE-SYNTAX   TestIndicatorField,
  EQUALITY MATCHING-RULE  booleanMatch,
  NUMERATION              single-valued,
  ID                      id-rat-test-indicator-for-this-recipient
}

--	END Fields from EDIFACT
--	Fields from ANSIX12 ISA
authorization-information-for-this-recipient X413ATTRIBUTE ::= {
  WITH ATTRIBUTE-SYNTAX  AuthorizationInformationField,
                           
  -- EQUALITY MATCHING-RULE   rule not defined 
  NUMERATION             single-valued,
  ID                     id-rat-authorization-information-for-this-recipient
}

--	END Fields from ANSIX12 ISA
recipient-extensions-for-this-recipient X413ATTRIBUTE ::= {
  WITH ATTRIBUTE-SYNTAX  RecipientExtensionsSubField,
                           
  -- EQUALITY MATCHING-RULE   rule not defined 
  NUMERATION             multi-valued,
  ID                     id-rat-recipient-extensions-for-this-recipient
}

--	Body Attributes
--	Body
body X413ATTRIBUTE ::= {
  WITH ATTRIBUTE-SYNTAX  Body,
  NUMERATION             single-valued,
  ID                     id-bat-body
}

--	Body Analyses
interchange-length X413ATTRIBUTE ::= {
  WITH ATTRIBUTE-SYNTAX   InterchangeLength,
  ORDERING MATCHING-RULE  integerOrderingMatch,
  NUMERATION              single-valued,
  ID                      id-bat-interchange-length
}

InterchangeLength ::= INTEGER

--	Primary Body Parts
edi-body-part X413ATTRIBUTE ::= {
  WITH ATTRIBUTE-SYNTAX  EDIBodyPart,
  NUMERATION             single-valued,
  ID                     id-bat-edi-body-part
}

edim-body-part X413ATTRIBUTE ::= {
  WITH ATTRIBUTE-SYNTAX
    SequenceNumber, -- sequence number of the forwarded EDIM entry
      
  NUMERATION             single-valued,
  ID                     id-bat-edim-body-part
}

message-parameters X413ATTRIBUTE ::= {
  WITH ATTRIBUTE-SYNTAX  MessageParameters,
  NUMERATION             single-valued,
  ID                     id-bat-message-parameters
}

message-data X413ATTRIBUTE ::= {
  WITH ATTRIBUTE-SYNTAX  MessageData,
  NUMERATION             single-valued,
  ID                     id-bat-message-data
}

--	Extended Body Part Types
extended-body-part-types X413ATTRIBUTE ::= {
  WITH ATTRIBUTE-SYNTAX   OBJECT IDENTIFIER,
  EQUALITY MATCHING-RULE  objectIdentifierMatch,
  NUMERATION              multi-valued,
  ID                      id-bat-extended-body-part-types
}

--	Description of the extended-body-part-types X413ATTRIBUTE syntax for parameter portion 
--	only
--EDIExtendedBodyPartParameterAttribute ::= SEQUENCE {
--	body-part-reference     [0] BodyPartReference OPTIONAL,
--	parameter               [1] EXTENDED-BODY-PART-TYPE.&parameters }
--	Notification Attributes
--	Common Fields
subject-edim X413ATTRIBUTE ::= {
  WITH ATTRIBUTE-SYNTAX   SubjectEDIMField,
  EQUALITY MATCHING-RULE  iPMIdentifierMatch,
  NUMERATION              single-valued,
  ID                      id-nat-subject-edim
}

edin-originator X413ATTRIBUTE ::= {
  WITH ATTRIBUTE-SYNTAX   EDINOriginatorField,
  EQUALITY MATCHING-RULE  oRNameMatch,
  NUMERATION              single-valued,
  ID                      id-nat-edin-originator
}

first-recipient X413ATTRIBUTE ::= {
  WITH ATTRIBUTE-SYNTAX   FirstRecipientField,
  EQUALITY MATCHING-RULE  oRNameMatch,
  NUMERATION              single-valued,
  ID                      id-nat-first-recipient
}

notification-time X413ATTRIBUTE ::= {
  WITH ATTRIBUTE-SYNTAX   NotificationTimeField,
  EQUALITY MATCHING-RULE  uTCTimeMatch,
  ORDERING MATCHING-RULE
    uTCTimeOrderingMatch, -- rule not defined in version 1 
      
  NUMERATION              single-valued,
  ID                      id-nat-notification-time
}

notification-security-elements X413ATTRIBUTE ::= {
  WITH ATTRIBUTE-SYNTAX  SecurityElementsField,
                           
  -- EQUALITY MATCHING-RULE   rule not defined 
  NUMERATION             single-valued,
  ID                     id-nat-notification-security-elements
}

edin-initiator X413ATTRIBUTE ::= {
  WITH ATTRIBUTE-SYNTAX   EDINInitiatorField,
  EQUALITY MATCHING-RULE  integerMatch,
  NUMERATION              single-valued,
  ID                      id-nat-edin-initiator
}

notification-extensions X413ATTRIBUTE ::= {
  WITH ATTRIBUTE-SYNTAX  NotificationExtensionsSubField,
                           
  -- EQUALITY MATCHING-RULE   rule not defined 
  NUMERATION             multi-valued,
  ID                     id-nat-notification-extensions
}

--	Positive Notification Extension Fields
pn-supplementary-information X413ATTRIBUTE ::= {
  WITH ATTRIBUTE-SYNTAX     EDISupplementaryInformation,
  EQUALITY MATCHING-RULE    mSStringMatch,
  SUBSTRINGS MATCHING-RULE  mSSubstringsMatch,
  NUMERATION                single-valued,
  ID                        id-nat-pn-supplementary-info
}

pn-extensions X413ATTRIBUTE ::= {
  WITH ATTRIBUTE-SYNTAX  PNExtensionsSubField,
                           
  -- EQUALITY MATCHING-RULE   rule not defined 
  NUMERATION             multi-valued,
  ID                     id-nat-pn-extensions
}

--	Negative Notification Fields
nn-reason-code X413ATTRIBUTE ::= {
  WITH ATTRIBUTE-SYNTAX  NNReasonCodeField,
                           
  -- EQUALITY MATCHING-RULE   rule not defined 
  NUMERATION             single-valued,
  ID                     id-nat-nn-reason-code
}

nn-supplementary-information X413ATTRIBUTE ::= {
  WITH ATTRIBUTE-SYNTAX     EDISupplementaryInformation,
  EQUALITY MATCHING-RULE    mSStringMatch,
  SUBSTRINGS MATCHING-RULE  mSSubstringsMatch,
  NUMERATION                single-valued,
  ID                        id-nat-nn-supplementary-info
}

nn-extensions X413ATTRIBUTE ::= {
  WITH ATTRIBUTE-SYNTAX  NNExtensionsSubField,
                           
  -- EQUALITY MATCHING-RULE   rule not defined 
  NUMERATION             multi-valued,
  ID                     id-nat-nn-extensions
}

--	Forwarded Fields
forwarded-to X413ATTRIBUTE ::= {
  WITH ATTRIBUTE-SYNTAX   ForwardedTo,
  EQUALITY MATCHING-RULE  oRNameMatch,
  NUMERATION              single-valued,
  ID                      id-nat-forwarded-to
}

fn-reason-code X413ATTRIBUTE ::= {
  WITH ATTRIBUTE-SYNTAX  FNReasonCodeField,
                           
  -- EQUALITY MATCHING-RULE   rule not defined 
  NUMERATION             single-valued,
  ID                     id-nat-fn-reason-code
}

fn-supplementary-information X413ATTRIBUTE ::= {
  WITH ATTRIBUTE-SYNTAX     EDISupplementaryInformation,
  EQUALITY MATCHING-RULE    mSStringMatch,
  SUBSTRINGS MATCHING-RULE  mSSubstringsMatch,
  NUMERATION                single-valued,
  ID                        id-nat-fn-supplementary-info
}

fn-extensions X413ATTRIBUTE ::= {
  WITH ATTRIBUTE-SYNTAX  FNExtensionsSubField,
                           
  -- EQUALITY MATCHING-RULE   rule not defined 
  NUMERATION             multi-valued,
  ID                     id-nat-fn-extensions
}

--	Correlation attributes
ac-forwarding-edims X413ATTRIBUTE ::= {
  WITH ATTRIBUTE-SYNTAX   SequenceNumber,
  EQUALITY MATCHING-RULE  integerMatch,
  ORDERING MATCHING-RULE  integerOrderingMatch,
  NUMERATION              multi-valued,
  ID                      id-cat-forwarding-edims
}

ac-forwarded-edims X413ATTRIBUTE ::= {
  WITH ATTRIBUTE-SYNTAX   SequenceNumber,
  EQUALITY MATCHING-RULE  integerMatch,
  ORDERING MATCHING-RULE  integerOrderingMatch,
  NUMERATION              multi-valued,
  ID                      id-cat-forwarded-edims
}

ac-obsoleting-edims X413ATTRIBUTE ::= {
  WITH ATTRIBUTE-SYNTAX   SequenceNumber,
  EQUALITY MATCHING-RULE  integerMatch,
  ORDERING MATCHING-RULE  integerOrderingMatch,
  NUMERATION              multi-valued,
  ID                      id-cat-obsoleting-edims
}

ac-obsoleted-edims X413ATTRIBUTE ::= {
  WITH ATTRIBUTE-SYNTAX  EDIMLocation,
  OTHER MATCHING-RULES
    {iPMLocationMatch, ...}, -- from ITU-T Rec. X.420 |ISO/IEC 10021-7
      
  NUMERATION             multi-valued,
  ID                     id-cat-obsoleted-edims
}

EDIMLocation ::= CHOICE {stored  SET OF SequenceNumber,
                         absent  NULL,
                         ...
}

ac-relating-edims X413ATTRIBUTE ::= {
  WITH ATTRIBUTE-SYNTAX   SequenceNumber,
  EQUALITY MATCHING-RULE  integerMatch,
  ORDERING MATCHING-RULE  integerOrderingMatch,
  NUMERATION              multi-valued,
  ID                      id-cat-relating-edims
}

ac-related-edims X413ATTRIBUTE ::= {
  WITH ATTRIBUTE-SYNTAX  EDIMLocation,
  OTHER MATCHING-RULES   {iPMLocationMatch, ...},
  NUMERATION             multi-valued,
  ID                     id-cat-related-edims
}

ac-subject-edim X413ATTRIBUTE ::= {
  WITH ATTRIBUTE-SYNTAX   SequenceNumber,
  EQUALITY MATCHING-RULE  integerMatch,
  ORDERING MATCHING-RULE  integerOrderingMatch,
  NUMERATION              single-valued,
  ID                      id-cat-subject-edim
}

ac-edim-recipients X413ATTRIBUTE ::= {
  WITH ATTRIBUTE-SYNTAX   ORName,
  EQUALITY MATCHING-RULE  oRNameMatch,
  OTHER MATCHING-RULES
    {oRNameElementsMatch | oRNameSubstringElementsMatch |
      oRNameSingleElementMatch},
  NUMERATION              multi-valued,
  ID                      id-cat-edim-recipients
}

ac-delivered-edin-summary X413ATTRIBUTE ::= {
  WITH ATTRIBUTE-SYNTAX   EDINStatus,
  EQUALITY MATCHING-RULE  bitStringMatch,
  NUMERATION              multi-valued,
  ID                      id-cat-delivered-edin-summary
}

EDINStatus ::= BIT STRING {
  nn-requested(0), fn-requested(1), pn-requested(2), nn-issued(3),
  fn-issued(4), pn-issued(5)}

ac-correlated-delivered-edins X413ATTRIBUTE ::= {
  WITH ATTRIBUTE-SYNTAX  CorrelatedDeliveredEDINs,
  NUMERATION             multi-valued,
  ID                     id-cat-correlated-delivered-edins
}

CorrelatedDeliveredEDINs ::= CHOICE {
  no-edin-received  [0]  NULL,
  edins-received    [1]  SEQUENCE OF SequenceNumber
}

ac-submitted-edin-status X413ATTRIBUTE ::= {
  WITH ATTRIBUTE-SYNTAX   EDINStatus,
  EQUALITY MATCHING-RULE  bitStringMatch,
  NUMERATION              single-valued,
  ID                      id-cat-submitted-edin-status
}

ac-submitted-edins X413ATTRIBUTE ::= {
  WITH ATTRIBUTE-SYNTAX   SequenceNumber,
  EQUALITY MATCHING-RULE  integerMatch,
  ORDERING MATCHING-RULE  integerOrderingMatch,
  NUMERATION              multi-valued,
  ID                      id-cat-submitted-edins
}

END -- of EDIMSMessageStoreAttributes

-- Generated by Asnp, the ASN.1 pretty-printer of France Telecom R&D

Example3-ELM


-- Generated by Ecnp, the pretty-printer of France Telecom R&amp;D

Example3-ELM {joint-iso-itu-t(2) asn1(1) ecn(4) examples(5) elm-module3(8)}
LINK-DEFINITIONS ::=
BEGIN

IMPORTS
  Example3Encodings, #Sequence1, #Sequence2, #Octet3, #Sequence3,
    #SequenceOfIntegers
    FROM Example3-EDM {joint-iso-itu-t(2) asn1(1) ecn(4) examples(5)
      edm-module3(10)};

ENCODE #Sequence1, #Sequence2, #Octet3, #Sequence3, #SequenceOfIntegers
    WITH Example3Encodings COMPLETED BY PER-BASIC-UNALIGNED

END

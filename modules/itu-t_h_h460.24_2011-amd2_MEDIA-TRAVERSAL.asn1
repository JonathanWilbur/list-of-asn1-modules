MEDIA-TRAVERSAL (H.406.24:03/2013)


-- Module MEDIA-TRAVERSAL (H.406.24:03/2013)
-- See also ITU-T H.460.24 (2009) Amd. 2 (03/2013)
-- See also the index of all ASN.1 assignments needed in this document

MEDIA-TRAVERSAL {itu-t(0) recommendation(0) h(8) 460 24 2 asn1-module(1)}
DEFINITIONS AUTOMATIC TAGS ::=
BEGIN

IMPORTS TransportAddress
          FROM MULTIMEDIA-SYSTEM-CONTROL -- See Rec. ITU-T H.245
            ;

AlternateAddresses ::= SEQUENCE {addresses  SEQUENCE OF AlternateAddress,
                                 ...
}

AlternateAddress ::= SEQUENCE {
  sessionID       INTEGER(0..255),
  sessionCUI      IA5String OPTIONAL,
  rtpAddress      TransportAddress OPTIONAL,
  rtcpAddress     TransportAddress OPTIONAL,
  ...,
  multiplexID     INTEGER(0..4294967295) OPTIONAL
}

END

-- Generated by Asnp, the ASN.1 pretty-printer of France Telecom R&D

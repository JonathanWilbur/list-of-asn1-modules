Conference-Add-On-Operations (Q.954.1:03/1993)


-- Module Conference-Add-On-Operations (Q.954.1:03/1993)
-- See also ITU-T Q.954.1 (03/1993)
-- See also the index of all ASN.1 assignments needed in this document

Conference-Add-On-Operations {itu-t(0) recommendation(0) q(17) q954(954)
  part1(1) operations-and-errors(1)} DEFINITIONS ::=
BEGIN

EXPORTS
  beginCONF, addCONF, splitCONF, dropCONF, isolateCONF, reattachCONF,
    partyDISC, floatCONF, endCONF, illConferenceId, illPartyId,
    numberOfPartiesExceeded, notActive, notAllowed, PartyId, ConferenceId,
    ConfSize;

IMPORTS
  OPERATION, ERROR
    FROM Remote-Operations-Information-Objects {joint-iso-itu-t
      remote-operations(4) informationObjects(5) version1(0)}
  userNotSubscribed, notAvailable, resourceUnavailable, invalidCallState,
    supplementaryServiceInteractionNotAllowed
    FROM General-Error-List {itu-t recommendation q 950 general-error-list(1)};

beginCONF OPERATION ::= {
  ARGUMENT  ConfSize -- optional
  RESULT
    SEQUENCE {conferenceId  ConferenceId,
              partyId       PartyId OPTIONAL}
  ERRORS
    {userNotSubscribed | notAvailable | resourceUnavailable | invalidCallState}
  CODE      local:40
}

addCONF OPERATION ::= {
  ARGUMENT  ConferenceId
  RESULT    PartyId
  ERRORS
    {illConferenceId | numberOfPartiesExceeded | notAllowed |
      supplementaryServiceInteractionNotAllowed | invalidCallState}
  CODE      local:41
}

splitCONF OPERATION ::= {
  ARGUMENT  SEQUENCE {conferenceId  ConferenceId,
                      partyId       PartyId}
  ERRORS    {illConferenceId | illPartyId}
  CODE      local:42
}

dropCONF OPERATION ::= {
  ARGUMENT  PartyId
  ERRORS    {illPartyId | notActive}
  CODE      local:43
}

isolateCONF OPERATION ::= {
  ARGUMENT  PartyId
  ERRORS    {illPartyId | notActive}
  CODE      local:44
}

reattachCONF OPERATION ::= {
  ARGUMENT  PartyId
  ERRORS    {illPartyId | notActive}
  CODE      local:45
}

partyDISC OPERATION ::= {
  ARGUMENT  PartyId
  ERRORS    {illPartyId | notActive}
  CODE      local:46
}

floatCONF OPERATION ::= {ERRORS  {notActive | notAllowed}
                         CODE    local:47
}

endCONF OPERATION ::= {ERRORS  {notActive}
                       CODE    local:48
}

identifyConferee OPERATION ::= {ARGUMENT  PartyId
                                CODE      local:49
}

illConferenceId ERROR ::= {CODE  local:28
}

illPartyId ERROR ::= {CODE  local:29
}

numberOfPartiesExceeded ERROR ::= {CODE  local:30
}

notActive ERROR ::= {CODE  local:31
}

notAllowed ERROR ::= {CODE  local:32
}

PartyId ::= INTEGER(0..127)

ConferenceId ::= INTEGER(0..127)

ConfSize ::= INTEGER(0..127)

END -- of Conference-Add-On-Operations

-- Generated by Asnp, the ASN.1 pretty-printer of France Telecom R&D

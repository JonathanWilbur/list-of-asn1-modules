COPSS1-Protocol (Q.765.1:05/1998)


-- Module COPSS1-Protocol (Q.765.1:05/1998)
-- See also ITU-T Q.765.1 (05/1998)
-- See also the index of all ASN.1 assignments needed in this document

COPSS1-Protocol {itu-t(0) recommendation(0) q(17) q765(765) q765-1(1)
  modules(2) operations-and-errors(1) version1(1)} DEFINITIONS IMPLICIT TAGS
::=
BEGIN

IMPORTS
  OPERATION, ERROR
    --FROM TCAP-Messages {itu-t Recommendation q 773 modules(2) messages(1) version2(2)}
    FROM Remote-Operations-Information-Objects {joint-iso-itu-t
      remote-operations(4) informationObjects(5) version1(0)};

-- TYPE DEFINITIONS FOR OPERATIONS
--Specification of Setup
--Direction:	OLEX ® DLEX
--Class:	3
--Timer:	T1
--Purpose:	Used for the establishment of a signalling association between a PIN and a PAN for a bearer unrelated signalling connection.
setUp OPERATION ::= {
  ARGUMENT  SetUpArg
  RESULT    SetUpResultArg
  CODE      global:{cOPSS1OID setUp(1)}
}

--Specification of Connect
--Direction:	DLEX ® OLEX
--Class:	4
--Purpose:	Indicates that the signalling connection has reached the active state.
connect OPERATION ::= {
  ARGUMENT  ConnectArg
  CODE      global:{cOPSS1OID connect(2)}
}

--Specification of Release
--Direction:	OLEX ® DLEX and DLEX ® OLEX
--Class:	4
--Purpose:	Used for releasing a signalling association between a PIN and a PAN.
release OPERATION ::= {
  ARGUMENT  ReleaseArg
  CODE      global:{cOPSS1OID release(3)}
}

--Specification of VpnFacility
--Direction:	OLEX ® DLEX and DLEX ® OLEX
--Class:	4
--Purpose:	Used for transporting PSS1 information flows during the active phase of a signalling connection.
vpnFacility OPERATION ::= {
  ARGUMENT  VpnFacilityArg
  CODE      global:{cOPSS1OID vpnFacility(4)}
}

--Specification of ActivityTest
--Direction:	OLEX ® DLEX
--Class:	3
--Timer:	T2
--Purpose:	Used to determine if the signalling association remains established between a PIN and a PAN.
activityTest OPERATION ::= {CODE  global:{cOPSS1OID activityTest(5)}
}

--TYPE DEFINITIONS FOR ERRORS
-- TYPE DEFINITIONS FOR ARGUMENT DATA
SetUpArg ::= SEQUENCE {
  calledPartyNumber  CalledPartyNumber,
  vpntransport       VPNTransport,
  ...
}

SetUpResultArg ::= SEQUENCE {
  cause         [0]  Cause OPTIONAL,
  vpntransport  [1]  VPNTransport OPTIONAL,
  ...
}

ConnectArg ::= VPNTransport

ReleaseArg ::= SEQUENCE {
  cause         Cause,
  vpntransport  [0]  VPNTransport OPTIONAL,
  ...
}

VpnFacilityArg ::= VPNTransport

--TYPE DEFINITIONS FOR DATA
CalledPartyNumber ::= OCTET STRING(SIZE (1..maxcdPlength))

--The CalledPartyNumber is coded as described in Recommendation Q.763 [13].
--The ISUP parameter name and length octets are not included.
VPNTransport ::= OCTET STRING(SIZE (0..maxLength))

--The VPNTransport is coded as described in clause 14/Q.765.1.
Cause ::= OCTET STRING(SIZE (1..maxCauseLength))

--The Cause is coded as described in ISO/IEC 11572 [2]/ Q.931 Annex M [21]
--The information element identifier and length octets are not included.
--DEFINITION OF RANGE CONSTANTS
maxCauseLength INTEGER ::=
  30

maxLength INTEGER ::= 2048

maxcdPlength INTEGER ::= 1 -- Network specific

--DEFINITION OF OBJECT IDENTIFIER PATH
cOPSS1OID OBJECT IDENTIFIER ::=
  {itu-t(0) recommendation(0) q(17) q765(765) q765-1(1) modules(2)
   operations-and-errors(1)} --of COPSS1-Protocol

END

-- Generated by Asnp, the ASN.1 pretty-printer of France Telecom R&D

SDHCSASN1 (G.774.5:02/2001)


-- Module SDHCSASN1 (G.774.5:02/2001)
-- See also ITU-T G.774.5 (02/2001)
-- See also the index of all ASN.1 assignments needed in this document

SDHCSASN1 {itu-t(0) recommendation(0) g(7) g774(774) hyphen(127) cs(5)
  informationModel(0) asn1Module(2) sdhcs(0)} DEFINITIONS IMPLICIT TAGS ::=
BEGIN

-- EXPORTS Everything
IMPORTS
  PathTrace
    FROM SDH {itu-t(0) recommendation(0) g(7) sdhm(774) informationModel(0)
      asn1Module(2) sdh(0)};

sdhCS OBJECT IDENTIFIER ::=
  {itu-t(0) recommendation(0) g(7) g774(774) hyphen(127) cs(5)
   informationModel(0)}

g774-05MObjectClass OBJECT IDENTIFIER ::= {sdhCS managedObjectClass(3)}

g774-05Package OBJECT IDENTIFIER ::= {sdhCS package(4)}

g774-05NameBinding OBJECT IDENTIFIER ::= {sdhCS nameBinding(6)}

g774-05Attribute OBJECT IDENTIFIER ::= {sdhCS attribute(7)}

Boolean ::= BOOLEAN

defaultNull Null ::= NULL

Null ::= NULL

PathTraceRS ::= GraphicString

END

-- Generated by Asnp, the ASN.1 pretty-printer of France Telecom R&D

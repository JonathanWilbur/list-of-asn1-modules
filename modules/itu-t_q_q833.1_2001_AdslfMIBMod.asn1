AdslfMIBMod (Q.833.1:01/2001)


-- Module AdslfMIBMod (Q.833.1:01/2001)
-- See also ITU-T Q.833.1 (01/2001)
-- See also the index of all ASN.1 assignments needed in this document

AdslfMIBMod {1 3 6 1 4 1 adslForum(3561) adslForumNetworkManagement(1)
  adslfLineMIB(1) informationModel(0) asn1Module(2) adslfMIBMod(0)} DEFINITIONS
IMPLICIT TAGS ::=
BEGIN

-- exports everything
IMPORTS
  Boolean, NameType, PointerOrNull, ProblemCause
    FROM ASN1DefinedTypesModule {itu-t recommendation m(13) gnm(3100)
      informationModel(0) asn1Modules(2) asn1DefinedTypesModule(0)}
  -- Note: DistinguishedName and RelativeDistinguishedName, formerly imported
  -- from X.501 InformationFramework, are imported from X.711 CMIP.
  DistinguishedName, RelativeDistinguishedName
    FROM CMIP-1 {joint-iso-itu-t ms(9) cmip(1) modules(0) protocol(3)}
  EventTypeId, ObjectInstance
    FROM CMIP-1 {joint-iso-itu-t ms(9) cmip(1) modules(0) protocol(3)}
  AdministrativeState, AttributeList, NotificationIdentifier, ProbableCause,
    SimpleNameType
    FROM Attribute-ASN1Module {joint-iso-itu-t ms(9) smi(3) part2(2)
      asn1Module(2) 1};

adslfNMInformationModel OBJECT IDENTIFIER ::=
  {1 3 6 1 4 1 adslForum(3561) adslForumNetworkManagement(1) adslfLineMIB(1)
   informationModel(0)}

adslfNMStandardSpecificExtension OBJECT IDENTIFIER ::=
  {adslfNMInformationModel 0}

adslfNMObjectClass OBJECT IDENTIFIER ::= {adslfNMInformationModel 3}

adslfNMPackage OBJECT IDENTIFIER ::= {adslfNMInformationModel 4}

adslfNMAttribute OBJECT IDENTIFIER ::= {adslfNMInformationModel 5}

adslfNMNameBinding OBJECT IDENTIFIER ::= {adslfNMInformationModel 6}

adslfNMAction OBJECT IDENTIFIER ::= {adslfNMInformationModel 7}

adslfNMNotification OBJECT IDENTIFIER ::= {adslfNMInformationModel 8}

-- default value definitions
booleanFalseDefault Boolean ::= FALSE

booleanTrueDefault Boolean ::= TRUE

integerZero INTEGER ::= 0

-- Additional probableCause Definitions
adslfNMProbableCause OBJECT IDENTIFIER ::=
  {adslfNMStandardSpecificExtension 0}

lossOfPower ProbableCause ::= globalValue:{adslfNMProbableCause 1}

lossOfLink ProbableCause ::= globalValue:{adslfNMProbableCause 2}

lossOfSignalQuality ProbableCause ::= globalValue:{adslfNMProbableCause 3}

dataInitFailure ProbableCause ::= globalValue:{adslfNMProbableCause 4}

configInitFailure ProbableCause ::= globalValue:{adslfNMProbableCause 5}

protocolInitFailure ProbableCause ::= globalValue:{adslfNMProbableCause 6}

noPeerAtuPresent ProbableCause ::= globalValue:{adslfNMProbableCause 7}

-- Additional eventTypes Definitions
adslfNMEventTypes OBJECT IDENTIFIER ::=
  {adslfNMStandardSpecificExtension 1}

-- Supporting productions
AdslAvailabilityStatus ::= SET OF AdslLineCondition

AdslChannelOptions ::= ENUMERATED {
  noChannels(0), fastOnly(1), interleavedOnly(2), fastOrInterleaved(3),
  fastAndInterleaved(4)}

AdslChannelType ::= ENUMERATED {fast(0), interleaved(1)}

AdslInitFailedInfo ::= SEQUENCE {
  probableCause           ProbableCause,
  notificationIdentifier  NotificationIdentifier OPTIONAL
}

AdslLineCoding ::= ENUMERATED {other(0), dmt(1), cap(2), qam(3)}

AdslLineCondition ::= ENUMERATED {
  lossOfFraming(0), lossOfSignal(1), lossOfPower(2), lossOfLink(3),
  lossOfSignalQuality(4), dataInitFailure(5), configInitFailure(6),
  protocolInitFailure(8), noPeerAtuPresent(9), lowPowerMode(10)}

-- ADSL modem Operational Mode
AdslOperationalMode ::= ENUMERATED {
  ansi(0), -- ANSI T1.413
  etsi(1), -- ETSI DTS/TM06006
  potsNonOverlapped(2), -- ITU G.992.1 POTS non-overlapped
  potsOverlapped(3), -- ITU G.992.1 POTS overlapped
  isdnNonOverlapped(4), -- ITU G.992.1 ISDN non-overlapped
  isdnOverlapped(5), -- ITU G.992.1 ISDN overlapped
  isdnTcm(6), -- ITU G.992.1 with TCM-ISDN
  potsNonOverlappedLite(7), -- ITU G.992.2 POTS non-overlapped
  potsOverlappedLite(8), -- ITU G.992.2 POTS overlapped
  isdnTcmLite(9)} -- ITU G.992.2 with TCM-ISDN

AdslOperationalModes ::= SET OF AdslOperationalMode

AdslRateChangeInfo ::= SEQUENCE {
  oldRate                 Integer,
  newRate                 Integer,
  notificationIdentifier  NotificationIdentifier OPTIONAL
}

AdslRateMode ::= ENUMERATED {fixed(0), adaptAtStartup(1), adaptAtRuntime(2)}

Integer ::= INTEGER

END

-- Generated by Asnp, the ASN.1 pretty-printer of France Telecom R&D

CommObject (H.350:05/2011)


-- Module CommObject (H.350:05/2011)
-- See also ITU-T H.350 (05/2011)
-- See also the index of all ASN.1 assignments needed in this document

CommObject {itu-t(0) recommendation(0) h(8) 350 1 cr(1) commObject(2) 
  module(4)} DEFINITIONS ::=
BEGIN

-- Communication Object Schema
-- Schema for Representing Communication Objects in an LDAP Directory
-- Abstract
-- This document defines the schema for representing Communication 
-- objects in an LDAP directory [LDAPv3].  It defines schema elements
-- to represent a communication object [commObject].
--                     .1 = Communication related work 
--                     .1.2 = commObject
--                     .1.2.1 = attributes
--                     .1.2.2 = objectclass
--                     .1.2.3 = syntax
-- Attribute Type Definitions
--    The following attribute types are defined in this document:
--        commUniqueId
--        commOwner
--        commPrivate
IMPORTS
  -- from Rec. ITU-T H.350
  h350-cr, caseIgnoreIA5Match, caseIgnoreIA5SubstringsMatch
    FROM CommURI {itu-t(0) recommendation(0) h(8) 350 1 cr(1) commURI(1)
      module(4)}
  -- from Rec. ITU-T X.501 | ISO/IEC 9594-2
  ATTRIBUTE, OBJECT-CLASS, top
    FROM InformationFramework {joint-iso-itu-t ds(5) module(1)
      informationFramework(1) 6}
  -- from Rec. ITU-T X.520 | ISO/IEC 9594-6
  UnboundedDirectoryString, caseExactMatch
    FROM SelectedAttributeTypes {joint-iso-itu-t ds(5) module(1)
      selectedAttributeTypes(5) 6};

commUniqueId ATTRIBUTE ::= {
  WITH SYNTAX               IA5String
  EQUALITY MATCHING RULE    caseIgnoreIA5Match
  SUBSTRINGS MATCHING RULE  caseIgnoreIA5SubstringsMatch
  ID                        {at  1}
}

commOwner ATTRIBUTE ::= {
  WITH SYNTAX             UnboundedDirectoryString
  EQUALITY MATCHING RULE  caseExactMatch
  ID                      {at  2}
}

commPrivate ATTRIBUTE ::= {WITH SYNTAX  IA5String
                           ID           {at  3}
}

-- Object Class Definitions
--    The following object classes are defined in this document:
--        commObject
-- commObject
commObject OBJECT-CLASS ::= {
  SUBCLASS OF   {top}
  MUST CONTAIN  {commUniqueId}
  MAY CONTAIN   {commOwner | commPrivate}
  ID            {oc  1}
}

co OBJECT IDENTIFIER ::= {h350-cr co(2)}

at OBJECT IDENTIFIER ::= {co at(1)}

oc OBJECT IDENTIFIER ::= {co oc(2)}

END -- end of ASN.1

-- Generated by Asnp, the ASN.1 pretty-printer of France Telecom R&D

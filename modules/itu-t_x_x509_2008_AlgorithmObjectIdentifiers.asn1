AlgorithmObjectIdentifiers (X.509:11/2008)


-- Module AlgorithmObjectIdentifiers (X.509:11/2008)
-- See also ITU-T X.509 (11/2008)
-- See also the index of all ASN.1 assignments needed in this document

AlgorithmObjectIdentifiers {joint-iso-itu-t ds(5) module(1)
  algorithmObjectIdentifiers(8) 6} DEFINITIONS ::=
BEGIN

-- EXPORTS All 
-- The types and values defined in this module are exported for use in the other ASN.1 modules contained 
-- within the Directory Specifications, and for the use of other applications which will use them to access 
-- Directory services. Other applications may use them for their own purposes, but this will not constrain
-- extensions and modifications needed to maintain or improve the Directory service.
IMPORTS
  algorithm, authenticationFramework
    FROM UsefulDefinitions {joint-iso-itu-t ds(5) module(1)
      usefulDefinitions(0) 6}
  ALGORITHM
    FROM AuthenticationFramework authenticationFramework;

-- categories of object identifier 
encryptionAlgorithm OBJECT IDENTIFIER ::=
  {algorithm 1}

hashAlgorithm OBJECT IDENTIFIER ::= {algorithm 2}

signatureAlgorithm OBJECT IDENTIFIER ::= {algorithm 3}

-- synonyms 
id-ea OBJECT IDENTIFIER ::= encryptionAlgorithm

id-ha OBJECT IDENTIFIER ::= hashAlgorithm

id-sa OBJECT IDENTIFIER ::= signatureAlgorithm

-- algorithms 
rsa ALGORITHM ::= {KeySize
                   IDENTIFIED BY  id-ea-rsa
}

KeySize ::= INTEGER

-- the following object identifier assignments reserve values assigned to deprecated functions
id-ea-rsa OBJECT IDENTIFIER ::=
  {id-ea 1}

id-ha-sqMod-n OBJECT IDENTIFIER ::= {id-ha 1}

id-sa-sqMod-nWithRSA OBJECT IDENTIFIER ::= {id-sa 1}

END -- AlgorithmObjectIdentifiers

-- Generated by Asnp, the ASN.1 pretty-printer of France Telecom R&D

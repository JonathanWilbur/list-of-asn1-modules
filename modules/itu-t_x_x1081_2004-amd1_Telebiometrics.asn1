Telebiometrics (X.1081:10/2009)


    -- Module Telebiometrics (X.1081:10/2009)
    -- See also ITU-T X.1081 (2004) Amd.1 (10/2009)
    -- See also the index of all ASN.1 
    assignments needed in this document

Telebiometrics {joint-iso-itu-t(2) telebiometrics(42) tmm(1) modules(0) 
  main(0) version(0)} 
  "/Telebiometrics/TMM/Modules/Main_Module/First_Version"
DEFINITIONS ::=
BEGIN

-- *1* OBJECT IDENTIFIER names for top-level biometric nodes
id-telebio OBJECT IDENTIFIER ::=
  {joint-iso-itu-t(2) telebiometrics(42)}

id-tmm OBJECT IDENTIFIER ::= {id-telebio tmm(1)}

id-hum-phys OBJECT IDENTIFIER ::= {id-telebio human-physiology(2)}

id-th OBJECT IDENTIFIER ::= {id-telebio telehealth(3)}

-- *2* OID-IRI or RELATIVE-OID-IRI names for top-level telebiometric nodes
-- Note that all RELATIVE-OID-IRI names are relative to the last RELATIVE-OID-IRI
-- value specified in this module
iri-telebio OID-IRI ::= "/Telebiometrics"

iri-tmm RELATIVE-OID-IRI ::= "TMM"

iri-hum-phys RELATIVE-OID-IRI ::= "Human_Physiology"

iri-th RELATIVE-OID-IRI ::= "Telehealth"

-- *3* OBJECT IDENTIFIER allocations specific to ITU-T X.1081
id-measures OBJECT IDENTIFIER ::= {id-tmm metric(1)}

id-fields-of-study OBJECT IDENTIFIER ::= {id-tmm scientific(2)}

id-modalities OBJECT IDENTIFIER ::= {id-tmm sensory(3)}

-- *3.1* OIDs for measures
id-quantities OBJECT IDENTIFIER ::= {id-measures quantities(1)}

id-units OBJECT IDENTIFIER ::= {id-measures units(2)}

id-symbols OBJECT IDENTIFIER ::= {id-measures symbols(3)}

-- *3.2* OIDs for fields of study
id-physics OBJECT IDENTIFIER ::= {id-fields-of-study physics(1)}

id-chemistry OBJECT IDENTIFIER ::= {id-fields-of-study chemistry(2)}

id-biology OBJECT IDENTIFIER ::= {id-fields-of-study biology(3)}

id-culturology OBJECT IDENTIFIER ::= {id-fields-of-study culturology(4)}

id-psychology OBJECT IDENTIFIER ::= {id-fields-of-study psychology(5)}

-- *3.3* OIDs for modalities
id-tango OBJECT IDENTIFIER ::= {id-modalities tango(1)}

id-video OBJECT IDENTIFIER ::= {id-modalities video(2)}

id-audio OBJECT IDENTIFIER ::= {id-modalities audio(3)}

id-chemo OBJECT IDENTIFIER ::= {id-modalities chemo(4)}

id-radio OBJECT IDENTIFIER ::= {id-modalities radio(5)}

id-calor OBJECT IDENTIFIER ::= {id-modalities calor(6)}

-- *4* RELATIVE-OID-IRI allocations specific to ITU-T X.1081
--    These are all relative to iri-tmm
iri-measures RELATIVE-OID-IRI ::= "Measures"

iri-fields-of-study RELATIVE-OID-IRI ::= "Fields_of_study"

iri-modalities RELATIVE-OID-IRI ::= "Modalities"

-- *4.1* OID-IRIs for Fields of Study
iri-quantities RELATIVE-OID-IRI ::= "Measures/Quantities"

iri-units RELATIVE-OID-IRI ::= "Measures/Units"

iri-symbols RELATIVE-OID-IRI ::= "Measures/Symbols"

-- *4.2* OID-IRIs for Fields of Study
iri-physics RELATIVE-OID-IRI ::= "Fields_of_Study/Physics"

iri-chemistry RELATIVE-OID-IRI ::= "Fields_of_Study/Chemistry"

iri-biology RELATIVE-OID-IRI ::= "Fields_of_Study/Biology"

iri-culturology RELATIVE-OID-IRI ::= "Fields_of_Study/Culturology"

iri-psychology RELATIVE-OID-IRI ::= "Fields_of_Study/Psychology"

-- *4.3* OID-IRIs for ModalitiesFields of Study
iri-tango RELATIVE-OID-IRI ::= "Modalities/Tango"

iri-video RELATIVE-OID-IRI ::= "Modalities/Video"

iri-audio RELATIVE-OID-IRI ::= "Modalities/Audio"

iri-chemo RELATIVE-OID-IRI ::= "Modalities/Chemo"

iri-radio RELATIVE-OID-IRI ::= "Modalities/Radio"

iri-calor RELATIVE-OID-IRI ::= "Modalities/Calor"

END

-- Generated by Asnp, the ASN.1 pretty-printer of France Telecom R&D

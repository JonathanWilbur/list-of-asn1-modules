IN-CS-1-Codes-appendix (Q.1218:10/1995)


-- Module IN-CS-1-Codes-appendix (Q.1218:10/1995)
-- See also ITU-T Q.1218 (10/1995)
-- See also the index of all ASN.1 assignments needed in this document

IN-CS-1-Codes-appendix {itu-t recommendation q 1218 modules(0)
  cs-1-codes-app(7) version1(0)} DEFINITIONS IMPLICIT TAGS ::=
BEGIN

-- OPERATION AND ERROR CODE ASSIGNMENTS FOR THE IN CS-1 PROTOCOL FOLLOW
IMPORTS
  OPERATION, Code
    FROM Remote-Operations-Information-Objects {joint-iso-itu-t
      remote-operations(4) informationObjects(5) version1(0)};

--  OPERATION AND ERROR CODE DEFINITION
--  Code point values are for further study. The operations are grouped by the identified ASEs.
--  Call party handling ASE
op-addParty Code ::=
  local:1

op-changeParties Code ::= local:2

op-holdCallPartyConnection Code ::= local:3

op-reconnect Code ::= local:4

op-releaseCallPartyConnection Code ::= local:5

op-attach Code ::= local:6

op-detach Code ::= local:7

-- ERROR codes
err-tooLate Code ::= local:19

err-legIDAlreadyAssigned Code ::= local:20

err-dataunavailable Code ::= local:21

err-dataAlreadyExists Code ::= local:22

END

-- Generated by Asnp, the ASN.1 pretty-printer of France Telecom R&D

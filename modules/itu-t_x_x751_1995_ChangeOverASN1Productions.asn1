ChangeOverASN1Productions (X.751:11/1995)


-- Module ChangeOverASN1Productions (X.751:11/1995)
-- See also ITU-T X.751 (1995) Technical Cor. 2 (02/2000)
-- See also the index of all ASN.1 assignments needed in this document

ChangeOverASN1Productions {joint-iso-itu-t ms(9) function(2) part17(17)
  asn1Module(2) 0} DEFINITIONS ::=
BEGIN

IMPORTS
  CMIP-ATTRIBUTE, AttributeSet, ObjectInstance, Attribute, ModifyOperator
    FROM CMIP-1 {joint-iso-itu-t ms(9) cmip(1) modules(0) protocol(3)};

ZeroToOne ::= INTEGER(0..1)

OneToOne ::= INTEGER(1..1)

OneToN ::= INTEGER(1..MAX)

part17Action OBJECT IDENTIFIER ::=
  {joint-iso-itu-t ms(9) function(2) part17(17) action(9)}

part17Attribute OBJECT IDENTIFIER ::=
  {joint-iso-itu-t ms(9) function(2) part17(17) attribute(7)}

part17MObjectClass OBJECT IDENTIFIER ::=
  {joint-iso-itu-t ms(9) function(2) part17(17) managedObjectClass(3)}

part17Package OBJECT IDENTIFIER ::=
  {joint-iso-itu-t ms(9) function(2) part17(17) package(4)}

part17Parameter OBJECT IDENTIFIER ::=
  {joint-iso-itu-t ms(9) function(2) part17(17) parameter(5)}

part17MRelClass OBJECT IDENTIFIER ::=
  {joint-iso-itu-t ms(9) function(2) part17(17) relationshipClass(11)}

part17Role OBJECT IDENTIFIER ::=
  {joint-iso-itu-t ms(9) function(2) part17(17) relationshipRole(13)}

BackUpInfo ::= SEQUENCE {
  backedUpObjectSpecified  [0]  OptionalObject DEFAULT noObject:NULL,
  backUpObjectSpecified    [1]  OptionalObject DEFAULT noObject:NULL,
  backedUpObjectExisting   [2]  OptionalObject DEFAULT noObject:NULL,
  backUpObjectExisting     [3]  OptionalObject DEFAULT noObject:NULL
}

BackUpObject ::= OptionalObject

ChangeBackInfo ::= SEQUENCE {
  backedUpObject         [0]  ObjectInstance,
  backUpObject           [1]  OptionalObject DEFAULT noObject:NULL,
  backedUpObjectChanges  [2] IMPLICIT ExpectedAttributeList OPTIONAL,
  backUpObjectChanges    [3] IMPLICIT ExpectedAttributeList OPTIONAL
}

ChangeOverInfo ::= SEQUENCE {
  primary           [0]  ObjectInstance,
  secondary         [1]  OptionalObject DEFAULT noObject:NULL,
  primaryChanges    [2] IMPLICIT ExpectedAttributeList OPTIONAL,
  secondaryChanges  [3] IMPLICIT ExpectedAttributeList OPTIONAL
}

Condition ::= SEQUENCE {object   ObjectInstance,
                        details  SET OF Attribute
}

-- At least one of the two components of Conditions must be present
Conditions ::= SEQUENCE {
  primary    [0] IMPLICIT Condition OPTIONAL,
  secondary  [1] IMPLICIT Condition OPTIONAL
}

ExpectedAttributeList ::=
  SET OF
    SEQUENCE {modifyOperator  [0] IMPLICIT ModifyOperator DEFAULT replace,
              attributeId     [1]  CMIP-ATTRIBUTE.&id({AttributeSet}),
              attributeValue
                [2]  CMIP-ATTRIBUTE.&Value({AttributeSet}{@.attributeId})
                  OPTIONAL}

NoSuchParticipant ::= SEQUENCE {
  role            [0]  OBJECT IDENTIFIER,
  objectInstance  [1]  ObjectInstance
}

NoSuchRelationship ::= SEQUENCE {
  relationshipClass     OBJECT IDENTIFIER,
  relationshipBinding   OBJECT IDENTIFIER OPTIONAL,
  relationshipInstance  [0]  RelationshipInstance OPTIONAL
}

OptionalObject ::= CHOICE {noObject  NULL,
                           object    ObjectInstance
}

PrimaryObject ::= ObjectInstance

PrimaryObjectSpecified ::= OptionalObject

-- At least one of the two components of UnattainableAttributeList must be present
RelationshipInstance ::= SET OF ObjectInstance

UnattainableAttributeList ::= SEQUENCE {
  primaryChanges    [0] IMPLICIT ExpectedAttributeList OPTIONAL,
  secondaryChanges  [1] IMPLICIT ExpectedAttributeList OPTIONAL
}

END

-- Generated by Asnp, the ASN.1 pretty-printer of France Telecom R&D

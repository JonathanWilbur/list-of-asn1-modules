IN-errorcodes (Q.1248.1:07/2001)


-- Module IN-errorcodes (Q.1248.1:07/2001)
-- See also ITU-T Q.1248.1 (07/2001)
-- See also the index of all ASN.1 assignments needed in this document

IN-errorcodes {itu-t recommendation q 1248 modules(1) in-errorcodes(4)
  version1(0)} DEFINITIONS ::=
BEGIN

IMPORTS
  ros-InformationObjects
    FROM IN-object-identifiers {itu-t recommendation q 1248 modules(1)
      in-object-identifiers(0) version1(0)}
  Code
    FROM Remote-Operations-Information-Objects ros-InformationObjects;

errcode-canceled Code ::= local:0

errcode-cancelFailed Code ::= local:1

errcode-eTCFailed Code ::= local:3

errcode-improperCallerResponse Code ::= local:4

errcode-missingCustomerRecord Code ::= local:6

errcode-missingParameter Code ::= local:7

errcode-parameterOutOfRange Code ::= local:8

errcode-requestedInfoError Code ::= local:10

errcode-systemFailure Code ::= local:11

errcode-taskRefused Code ::= local:12

errcode-unavailableResource Code ::= local:13

errcode-unexpectedComponentSequence Code ::= local:14

errcode-unexpectedDataValue Code ::= local:15

errcode-unexpectedParameter Code ::= local:16

errcode-unknownLegID Code ::= local:17

errcode-unknownResource Code ::= local:18

-- Error codes for the IN CS2 error types follow 
errcode-scfReferral Code ::=
  local:21

errcode-scfTaskRefused Code ::= local:22

errcode-chainingRefused Code ::= local:23

errcode-executionError Code ::= local:10

END

-- Generated by Asnp, the ASN.1 pretty-printer of France Telecom R&D

ABC (X.694 (2004) Amd.1:05/2007)


-- Module ABC (X.694 (2004) Amd.1:05/2007)
-- See also ITU-T X.694 (2004) Amend. 1 (05/2007)
-- See also the index of all ASN.1 assignments needed in this document

ABC -- The module reference is not standardized
DEFINITIONS XER INSTRUCTIONS AUTOMATIC TAGS ::=
BEGIN

IMPORTS
  Xyz-type
    FROM XYZ
  String
    FROM XSD {joint-iso-itu-t asn1(1) specification(0) modules(0) xsd-module(2)
      version1(1)};

/* For a Version 2 mapping, the last component of the module
		      identifier would be version2(2) */
Abc-elem ::= [NAME AS UNCAPITALIZED] Xyz-type

Sub1-elem ::= [NAME AS UNCAPITALIZED] XSD.String

Sub2-elem ::= [NAME AS UNCAPITALIZED] XSD.String

Sub2-attr ::= [NAME AS UNCAPITALIZED] [ATTRIBUTE] XSD.String

ENCODING-CONTROL XER
	GLOBAL-DEFAULTS MODIFIED-ENCODINGS
	GLOBAL-DEFAULTS CONTROL-NAMESPACE
		"http://www.w3.org/2001/XMLSchema-instance"
	NAMESPACE ALL AS "http://example.com/abc"
END

-- Generated by Asnp, the ASN.1 pretty-printer of France Telecom R&amp;D

IN-SSF-SCF-pkgs-contracts-acs (Q.1248.2:07/2001)


-- Module IN-SSF-SCF-pkgs-contracts-acs (Q.1248.2:07/2001)
-- See also ITU-T Q.1248.2 (07/2001)
-- See also the index of all ASN.1 assignments needed in this document

IN-SSF-SCF-pkgs-contracts-acs {itu-t recommendation q 1248 modules(1)
  in-ssf-scf-pkgs-contracts-acs(9) version1(0)} DEFINITIONS ::=
BEGIN

-- This module describes the operation-packages, contracts and application-contexts used
--  over the SSF-SCF interface.
IMPORTS
  id-ac-ssf-scfGenericAC, id-ac-ssf-scfDPSpecificAC,
    id-ac-ssf-scfAssistHandoffAC, id-ac-ssf-scfServiceManagementAC,
    id-ac-scf-ssfGenericAC, id-ac-scf-ssfDPSpecificAC,
    id-ac-scf-ssfTrafficManagementAC, id-ac-scf-ssfINTrafficManagementAC,
    id-ac-scf-ssfServiceManagementAC, id-ac-scf-ssfStatusReportingAC,
    id-ac-scf-ssfTriggerManagementAC, id-ac-scf-ssfRouteMonitoringAC,
    id-ac-ssf-scfRouteMonitoringAC, id-inSsfToScfGeneric,
    id-inSsfToScfDpSpecific, id-inAssistHandoffSsfToScf, id-inScfToSsfGeneric,
    id-inScfToSsfDpSpecific, id-inScfToSsfTrafficManagement,
    id-inScfToSsfINTrafficManagement, id-inScfToSsfServiceManagement,
    id-inSsfToScfServiceManagement, id-inScfToSsfStatusReporting,
    id-inScfToSsfTriggerManagement, id-inScfToSsfRouteMonitoring,
    id-inSsfToScfRouteMonitoring, id-as-ssf-scfGenericAS,
    id-as-ssf-scfDpSpecificAS, id-as-assistHandoff-ssf-scfAS,
    id-as-scf-ssfGenericAS, id-as-scf-ssfDpSpecificAS,
    id-as-scf-ssfRouteMonitoringAS, id-as-ssf-scfRouteMonitoringAS,
    id-as-scf-ssfINTrafficManagementAS, id-as-scf-ssfTrafficManagementAS,
    id-as-scf-ssfServiceManagementAS, id-as-ssf-scfServiceManagementAS,
    id-as-scf-ssfStatusReportingAS, id-as-scf-ssfTriggerManagementAS,
    id-package-scfActivation, id-package-basicBCPDP, id-package-advancedBCPDP,
    id-package-srf-scfActivationOfAssist,
    id-package-assistConnectionEstablishment,
    id-package-genericDisconnectResource,
    id-package-nonAssistedConnectionEstablishment, id-package-connect,
    id-package-callHandling, id-package-bcsmEventHandling,
    id-package-chargingEventHandling, id-package-ssfCallProcessing,
    id-package-scfCallInitiation, id-package-timer, id-package-billing,
    id-package-charging, id-package-monitorRoute, id-package-trafficManagement,
    id-package-iNTrafficManagement, id-package-serviceManagementActivate,
    id-package-serviceManagementResponse, id-package-callReport,
    id-package-signallingControl, id-package-activityTest,
    id-package-statusReporting, id-package-cancel, id-package-cphResponse,
    id-package-entityReleased, id-package-triggerManagement,
    id-package-uSIHandling, id-package-facilityIEHandling,
    id-package-dpSpecificEventHandling, id-package-triggerCallManagement,
    ros-InformationObjects, common-classes, scf-srf-classes,
    scf-srf-Operations, scf-srf-Protocol, ssf-scf-classes, ssf-scf-Operations,
    tc-Messages, tc-NotationExtensions
    FROM IN-object-identifiers {itu-t recommendation q 1248 modules(1)
      in-object-identifiers(0) version1(0)}
  COMMON-BOUNDS, EmptyReturnable
    FROM IN-common-classes common-classes
  SCF-SSF-BOUNDS
    FROM IN-SSF-SCF-Classes ssf-scf-classes
  SCF-SRF-BOUNDS
    FROM IN-SCF-SRF-Classes scf-srf-classes
  CONTRACT, OPERATION-PACKAGE, OPERATION, ROS-OBJECT-CLASS
    FROM Remote-Operations-Information-Objects ros-InformationObjects
  TCMessage{}
    FROM TCAPMessages tc-Messages
  APPLICATION-CONTEXT, dialogue-abstract-syntax
    FROM TC-Notation-Extensions tc-NotationExtensions
  activateServiceFiltering{}, activityTest, analysedInformation{},
    analyseInformation{}, applyCharging{}, applyChargingReport{},
    assistRequestInstructions{}, authorizeTermination{}, callFiltering{},
    callGap{}, callInformationReport{}, callInformationRequest{}, cancel{},
    cancelStatusReportRequest{}, collectedInformation{}, collectInformation{},
    connect{}, connectToResource{}, continue, continueWithArgument{},
    createCallSegmentAssociation{}, createOrRemoveTriggerData{},
    disconnectForwardConnection, disconnectForwardConnectionWithArgument{},
    disconnectLeg{}, entityReleased{}, establishTemporaryConnection{},
    eventNotificationCharging{}, eventReportBCSM{}, eventReportFacility{},
    facilitySelectedAndAvailable{}, furnishChargingInformation{},
    holdCallInNetwork, initialDP{}, initiateCallAttempt{}, manageTriggerData{},
    mergeCallSegments{}, monitorRouteRequest{}, monitorRouteReport{},
    moveCallSegments{}, moveLeg{}, oAbandon{}, oAnswer{}, oCalledPartyBusy{},
    oDisconnect{}, oMidCall{}, oNoAnswer{}, originationAttempt{},
    originationAttemptAuthorized{}, oSuspended{}, reconnect{}, releaseCall{},
    reportUTSI{}, requestCurrentStatusReport{},
    requestEveryStatusChangeReport{}, requestFirstStatusMatchReport{},
    requestNotificationChargingEvent{}, requestReportBCSMEvent{},
    requestReportUTSI{}, requestReportFacilityEvent{}, resetTimer{},
    routeSelectFailure{}, selectFacility{}, selectRoute{},
    sendChargingInformation{}, sendFacilityInformation{}, sendSTUI{},
    serviceFilteringResponse{}, setServiceProfile{}, splitLeg{},
    statusReport{}, tAnswer{}, tBusy{}, tDisconnect{}, terminationAttempt{},
    termAttemptAuthorized{}, tMidCall{}, tNoAnswer{}, tSuspended{}
    FROM IN-SSF-SCF-ops-args ssf-scf-Operations
  playAnnouncement{}, promptAndCollectUserInformation{},
    promptAndReceiveMessage{}, scriptClose{}, scriptEvent{},
    scriptInformation{}, scriptRun{}, specializedResourceReport
    FROM IN-SCF-SRF-ops-args scf-srf-Operations
  specializedResourceControlPackage{}, scriptControlPackage{},
    messageControlPackage{}
    FROM IN-SCF-SRF-pkgs-contracts-acs scf-srf-Protocol;

-- The following three definitions are local short-hand notation for convenience.
B1 ::=
  COMMON-BOUNDS -- defined in Part 1 of Recommendation Q.1248

B2 ::= SCF-SSF-BOUNDS -- defined in this part (Part 2) of Recommendation Q.1248

B3 ::= SCF-SRF-BOUNDS -- defined in Part 3 of Recommendation Q.1248

networkSpecificB1 COMMON-BOUNDS ::= {NUM-OF-EXTENSIONS  1
}

-- The following instance of the parameter bound is just an example
networkSpecificB2 SCF-SSF-BOUNDS ::= {
  HIGH-LAYER-COMPATIBILITY-LENGTH                    5 -- example value
  MINIMUM-FOR-ACH-BILLING-CHARGING                   1 -- example value
  MAXIMUM-FOR-ACH-BILLING-CHARGING                   5 -- example value
  MINIMUM-FOR-BACKWARD-GVNS                          1 -- example value
  MAXIMUM-FOR-BACKWARD-GVNS                          5 -- example value
  MAXIMUM-FOR-BEARER-CAPABILITY                      5 -- example value
  MINIMUM-FOR-CALLED-DIRECTORY-NUMBER                1 -- example value
  MAXIMUM-FOR-CALLED-DIRECTORY-NUMBER                5 -- example value
  MINIMUM-FOR-CALLED-PARTY-NUMBER                    1 -- example value
  MAXIMUM-FOR-CALLED-PARTY-NUMBER                    5 -- example value
  MINIMUM-FOR-CALLED-PARTY-SUBADDRESS                1 -- example value
  MAXIMUM-FOR-CALLED-PARTY-SUBADDRESS                5 -- example value
  MINIMUM-FOR-CALLING-GEODETIC-LOCATION              1 -- example value
  MAXIMUM-FOR-CALLING-GEODETIC-LOCATION              10 -- example value
  MINIMUM-FOR-CALLING-PARTY-NUMBER                   1 -- example value
  MAXIMUM-FOR-CALLING-PARTY-NUMBER                   5 -- example value
  MINIMUM-FOR-CALLING-PARTY-SUBADDRESS               1 -- example value
  MAXIMUM-FOR-CALLING-PARTY-SUBADDRESS               5 -- example value
  MINIMUM-FOR-CALL-RESULT                            1 -- example value
  MAXIMUM-FOR-CALL-RESULT                            5 -- example value
  MINIMUM-FOR-CARRIER                                3 -- example value
  MAXIMUM-FOR-CARRIER                                10 -- example value
  MINIMUM-FOR-CAUSE                                  1 --examlpe value
  MAXIMUM-FOR-CAUSE                                  4 -- example value
  MINIMUM-FOR-DESTINATION                            1 --example value
  MAXIMUM-FOR-DESTINATION                            10 --exemple value
  MINIMUM-FOR-DIGITS                                 1 -- example value
  MAXIMUM-FOR-DIGITS                                 5 -- example value
  MINIMUM-FOR-DISPLAY                                1 -- example value
  MAXIMUM-FOR-DISPLAY                                5 -- example value
  MINIMUM-FOR-EVENT-SPECIFIC-CHARGING                1 -- example value
  MAXIMUM-FOR-EVENT-SPECIFIC-CHARGING                5 -- example value
  MINIMUM-FOR-EVENT-TYPE-CHARGING                    1 -- example value
  MAXIMUM-FOR-EVENT-TYPE-CHARGING                    5 -- example value
  MINIMUM-FOR-FCI-BILLING-CHARGING                   1 -- example value
  MAXIMUM-FOR-FCI-BILLING-CHARGING                   5 -- example value
  MINIMUM-FOR-FORWARD-GVNS                           1 -- example value
  MAXIMUM-FOR-FORWARD-GVNS                           5 -- example value
  MINIMUM-FOR-GENERIC-NAME                           1 -- example value
  MAXIMUM-FOR-GENERIC-NAME                           5 -- example value
  MINIMUM-FOR-GENERIC-NUMBER                         1 -- example value
  MAXIMUM-FOR-GENERIC-NUMBER                         5 -- example value
  MAXIMUM-FOR-INITIAL-TIME-INTERVAL                  5 -- example value
  MAXIMUM-FOR-IN-SERVICE-COMPATIBILITY               5 -- example value
  MINIMUM-FOR-IP-AVAILABLE                           1 -- example value
  MAXIMUM-FOR-IP-AVAILABLE                           5 -- example value
  MINIMUM-FOR-IP-SSP-CAPABILITIES                    1 -- example value
  MAXIMUM-FOR-IP-SSP-CAPABILITIES                    5 -- example value
  MINIMUM-FOR-ISDN-ACCESS-RELATED-INFO               1 -- example value
  MAXIMUM-FOR-ISDN-ACCESS-RELATED-INFO               10 -- example value
  MINIMUM-FOR-LOCATION-NUMBER                        1 -- example value
  MAXIMUM-FOR-LOCATION-NUMBER                        5 -- example value
  MAXIMUM-NB-OF-ROUTES                               3 --example value
  MINIMUM-FOR-MID-CALL-CONTROL-INFO                  1 -- example value
  MAXIMUM-FOR-MID-CALL-CONTROL-INFO                  5 -- example value
  MINIMUM-FOR-ORIGINAL-CALLED-PARTY-ID               1 -- example value
  MAXIMUM-FOR-ORIGINAL-CALLED-PARTY-ID               5 -- example value
  MINIMUM-FOR-REASON                                 1 -- example value
  MAXIMUM-FOR-REASON                                 5 -- example value
  MINIMUM-FOR-REDIRECTING-ID                         1 -- example value
  MAXIMUM-FOR-REDIRECTING-ID                         5 -- example value
  MINIMUM-FOR-REQUESTED-UTSI-NUM                     1 -- example value
  MAXIMUM-FOR-REQUESTED-UTSI-NUM                     5 -- example value
  MINIMUM-FOR-ROUTE-LIST                             1 -- example value
  MAXIMUM-FOR-ROUTE-LIST                             5 -- example value
  MINIMUM-FOR-ROUTING-NUMBER                         1 -- example value
  MAXIMUM-FOR-ROUTING-NUMBER                         5 -- example value
  MINIMUM-FOR-SCF-ID                                 1 -- example value
  MAXIMUM-FOR-SCF-ID                                 5 -- example value
  MINIMUM-FOR-SCI-BILLING-CHARGING                   1 -- example value
  MAXIMUM-FOR-SCI-BILLING-CHARGING                   5 -- example value
  MINIMUM-FOR-SDSS-INFORMATION                       1 -- example value
  MAXIMUM-FOR-SDSS-INFORMATION                       5 -- example value
  MINIMUM-FOR-SII                                    1 -- example value
  MAXIMUM-FOR-SII                                    5 -- example value
  MINIMUM-FOR-SF-BILLING-CHARGING                    1 -- example value
  MAXIMUM-FOR-SF-BILLING-CHARGING                    5 -- example value
  MINIMUM-FOR-USI-INFORMATION                        1 -- example value
  MAXIMUM-FOR-USI-INFORMATION                        5 -- example value
  MINIMUM-FOR-USI-SERVICE-INDICATOR                  1 -- example value
  MAXIMUM-FOR-USI-SERVICE-INDICATOR                  5 -- example value
  NUM-OF-BCSM-EVENT                                  4 -- example value
  NUM-OF-BCUSM-EVENT                                 4 -- example value
  NUM-OF-CHARGING-EVENT                              4 -- example value
  NUM-OF-COUNTERS                                    4 -- example value
  NUM-OF-CSAS                                        2 -- example value
  NUM-OF-CSS                                         2 -- example value
  NUM-OF-GENERIC-NUMBERS                             2 -- example value
  NUM-OF-INFO-ITEMS                                  1 -- example value
  NUM-OF-INPROFILE                                   1 -- example value
  NUM-OF-SEVERALTRIGGER                              5 -- example value
  NUM-OF-IN-SERVICE-COMPATIBILITY-ID                 2 -- example value
  NUM-OF-LEGS                                        2 -- example value
  NUM-OF-MESSAGE-IDS                                 2 -- example value
  MAXIMUM-FOR-AMOUNT                                 2 -- example value
  MAXIMUM-FOR-CALL-REFERENCE                         5 -- example value
  MAXIMUM-FOR-CNINFO                                 13 -- example value
  MAXIMUM-FOR-INITIAL-UNIT-INCREMENT                 2 -- example value
  MAXIMUM-FOR-SCALING-FACTOR                         2 -- example value
  MAXIMUM-FOR-SEGMENTS-PER-DATA-INTERVAL             5 -- example value
  MAXIMUM-FOR-UB-NB-CALL                             5 -- example value
  NUM-OF-ADDRESSES                                   5 -- example value
  MINIMUM-FOR-AAL-PARAMETERS                         1 -- example value
  MAXIMUM-FOR-AAL-PARAMETERS                         1 -- example value
  MINIMUM-FOR-ADDITIONAL-ATM-CELL-RATE               1 -- example value
  MAXIMUM-FOR-ADDITIONAL-ATM-CELL-RATE               1 -- example value
  MINIMUM-FOR-AESA-CALLED-PARTY                      1 -- example value
  MAXIMUM-FOR-AESA-CALLED-PARTY                      1 -- example value
  MINIMUM-FOR-AESA-CALLING-PARTY                     1 -- example value
  MAXIMUM-FOR-AESA-CALLING-PARTY                     1 -- example value
  MINIMUM-FOR-ATM-CELL-RATE                          1 -- example value
  MAXIMUM-FOR-ATM-CELL-RATE                          1 -- example value
  MINIMUM-FOR-CDVT-DESCRIPTOR                        1 -- example value
  MAXIMUM-FOR-CDVT-DESCRIPTOR                        1 -- example value
  MINIMUM-FOR-CONNECTION-IDENTIFIER                  1 -- example value
  MAXIMUM-FOR-CONNECTION-IDENTIFIER                  1 -- example value
  MINIMUM-FOR-CUMULATIVE-TRANSIT-DELAY               1 -- example value
  MAXIMUM-FOR-CUMULATIVE-TRANSIT-DELAY               1 -- example value
  MINIMUM-FOR-END-TO-END-TRANSIT-DELAY               1 -- example value
  MAXIMUM-FOR-END-TO-END-TRANSIT-DELAY               1 -- example value
  MINIMUM-FOR-GENERIC-IDENTIFIER                     1 -- example value
  MAXIMUM-FOR-GENERIC-IDENTIFIER                     1 -- example value
  MINIMUM-FOR-MIN-ACCEPTABLE-ATM-TRAFFIC-DESCRIPTOR  1 -- example value
  MAXIMUM-FOR-MIN-ACCEPTABLE-ATM-TRAFFIC-DESCRIPTOR  1 -- example value
  MINIMUM-FOR-ALTERNATIVE-ATM-TRAFFIC-DESCRIPTOR     1 -- example value
  MAXIMUN-FOR-ALTERNATIVE-ATM-TRAFFIC-DESCRIPTOR     1 -- example value
  MINIMUM-FOR-QOS-PARAMETER                          1 -- example value
  MAXIMUM-FOR-QOS-PARAMETER                          1 -- example value
  MINIMUM-FOR-BROADBAND-BEARER-CAPABILITY            1 -- example value
  MAXIMUM-FOR-BROADBAND-BEARER-CAPABILITY            1 -- example value
  MAXIMUM-GLOBAL-CALL-REFERENCE                      5 -- example value
  MAXIMUM-ALTERNATIVE-IDENTITIES                     5 -- example value
  MAXIMUM-NB-OF-ALTERNATIVE-IDENTITIES               1
 -- example value--}

networkSpecificB3 SCF-SRF-BOUNDS ::= {
  MINIMUM-FOR-ATTRIBUTES              1 -- example value
  MAXIMUM-FOR-ATTRIBUTES              5 -- example value
  MINIMUM-FOR-MAIL-BOX-ID             1 -- example value
  MAXIMUM-FOR-MAIL-BOX-ID             5 -- example value
  MINIMUM-FOR-MESSAGE-CONTENT         1 -- example value
  MAXIMUM-FOR-MESSAGE-CONTENT         5 -- example value
  MINIMUM-FOR-RECEIVED-INFORMATION    1 -- example value
  MAXIMUM-FOR-RECEIVED-INFORMATION    5 -- example value
  MAXIMUM-FOR-RECORDING-TIME          5 -- example value
  NUM-OF-MESSAGE-IDS                  2 -- example value
  MAXIMUM-FOR-RECORDED-MESSAGE-UNITS  5 -- example value
  NUM-OF-VARIABLE-PARTS               5
 -- example value--}

-- Application Contexts 
ssf-scfGenericAC APPLICATION-CONTEXT ::= {
  CONTRACT                  inSsfToScfGeneric
  DIALOGUE MODE             structured
  ABSTRACT SYNTAXES
    {dialogue-abstract-syntax | ssf-scfGenericAbstractSyntax}
  APPLICATION CONTEXT NAME  id-ac-ssf-scfGenericAC
}

ssf-scfDPSpecificAC APPLICATION-CONTEXT ::= {
  CONTRACT                  inSsfToScfDpSpecific
  DIALOGUE MODE             structured
  ABSTRACT SYNTAXES
    {dialogue-abstract-syntax | ssf-scfDpSpecificAbstractSyntax}
  APPLICATION CONTEXT NAME  id-ac-ssf-scfDPSpecificAC
}

ssf-scfAssistHandoffAC APPLICATION-CONTEXT ::= {
  CONTRACT                  inAssistHandoffSsfToScf
  DIALOGUE MODE             structured
  ABSTRACT SYNTAXES
    {dialogue-abstract-syntax | assistHandoff-ssf-scfAbstractSyntax}
  APPLICATION CONTEXT NAME  id-ac-ssf-scfAssistHandoffAC
}

ssf-scfServiceManagementAC APPLICATION-CONTEXT ::= {
  CONTRACT                  inSsfToScfServiceManagement
  DIALOGUE MODE             structured
  ABSTRACT SYNTAXES
    {dialogue-abstract-syntax | ssf-scfServiceManagementAbstractSyntax}
  APPLICATION CONTEXT NAME  id-ac-ssf-scfServiceManagementAC
}

scf-ssfGenericAC APPLICATION-CONTEXT ::= {
  CONTRACT                  inScfToSsfGeneric
  DIALOGUE MODE             structured
  ABSTRACT SYNTAXES
    {dialogue-abstract-syntax | ssf-scfGenericAbstractSyntax}
  APPLICATION CONTEXT NAME  id-ac-scf-ssfGenericAC
}

scf-ssfDPSpecificAC APPLICATION-CONTEXT ::= {
  CONTRACT                  inScfToSsfDpSpecific
  DIALOGUE MODE             structured
  ABSTRACT SYNTAXES
    {dialogue-abstract-syntax | scf-ssfDpSpecificAbstractSyntax}
  APPLICATION CONTEXT NAME  id-ac-scf-ssfDPSpecificAC
}

scf-ssfINTrafficManagementAC APPLICATION-CONTEXT ::= {
  CONTRACT                  inScfToSsfINTrafficManagement
  DIALOGUE MODE             structured
  ABSTRACT SYNTAXES
    {dialogue-abstract-syntax | scf-ssfINTrafficManagementAbstractSyntax}
  APPLICATION CONTEXT NAME  id-ac-scf-ssfINTrafficManagementAC
}

scf-ssfTrafficManagementAC APPLICATION-CONTEXT ::= {
  CONTRACT                  inScfToSsfTrafficManagement
  DIALOGUE MODE             structured
  ABSTRACT SYNTAXES
    {dialogue-abstract-syntax | scf-ssfTrafficManagementAbstractSyntax}
  APPLICATION CONTEXT NAME  id-ac-scf-ssfTrafficManagementAC
}

scf-ssfServiceManagementAC APPLICATION-CONTEXT ::= {
  CONTRACT                  inScfToSsfServiceManagement
  DIALOGUE MODE             structured
  ABSTRACT SYNTAXES
    {dialogue-abstract-syntax | scf-ssfServiceManagementAbstractSyntax}
  APPLICATION CONTEXT NAME  id-ac-scf-ssfServiceManagementAC
}

scf-ssfStatusReportingAC APPLICATION-CONTEXT ::= {
  CONTRACT                  inScfToSsfStatusReporting
  DIALOGUE MODE             structured
  ABSTRACT SYNTAXES
    {dialogue-abstract-syntax | scf-ssfStatusReportingAbstractSyntax}
  APPLICATION CONTEXT NAME  id-ac-scf-ssfStatusReportingAC
}

scf-ssfTriggerManagementAC APPLICATION-CONTEXT ::= {
  CONTRACT                  inScfToSsfTriggerManagement
  DIALOGUE MODE             structured
  ABSTRACT SYNTAXES
    {dialogue-abstract-syntax | scf-ssfTriggerManagementAbstractSyntax}
  APPLICATION CONTEXT NAME  id-ac-scf-ssfTriggerManagementAC
}

scf-ssfRouteMonitoringAC APPLICATION-CONTEXT ::= {
  CONTRACT                  inScfToSsfRouteMonitoring
  DIALOGUE MODE             structured
  ABSTRACT SYNTAXES
    {dialogue-abstract-syntax | scf-ssfRouteMonitoringAbstractSyntax}
  APPLICATION CONTEXT NAME  id-ac-scf-ssfRouteMonitoringAC
}

ssf-scfRouteMonitoringAC APPLICATION-CONTEXT ::= {
  CONTRACT                  inSsfToScfRouteMonitoring
  DIALOGUE MODE             structured
  ABSTRACT SYNTAXES
    {dialogue-abstract-syntax | ssf-scfRouteMonitoringAbstractSyntax}
  APPLICATION CONTEXT NAME  id-ac-ssf-scfRouteMonitoringAC
}

-- Contracts 
inSsfToScfGeneric CONTRACT ::= {
  -- dialogue initiated by SSF with InitialDP Operation
  --The inSsfToScfGeneric contract expresses the form of the service in which the SSF, 
  --a ROS object of class ssf, initiates the generic triggering approach contract. 
  --A ROS-object of class scf, responds to this contract.
  INITIATOR CONSUMER OF
    {activityTestPackage | exceptionInformPackage{networkSpecificB2} |
      scfActivationPackage{networkSpecificB1, networkSpecificB2}}
  RESPONDER CONSUMER OF
    {activityTestPackage |
      assistConnectionEstablishmentPackage{networkSpecificB1,
                                          networkSpecificB2} |
      bcsmEventHandlingPackage{networkSpecificB1, networkSpecificB2} |
      billingPackage{networkSpecificB2} |
      callHandlingPackage{networkSpecificB2} |
      callReportPackage{networkSpecificB1, networkSpecificB2} |
      cancelPackage{networkSpecificB2} |
      chargingEventHandlingPackage{networkSpecificB1, networkSpecificB2} |
      chargingPackage{networkSpecificB1, networkSpecificB2} |
      connectPackage{networkSpecificB1, networkSpecificB2} |
      cphResponsePackage{networkSpecificB1, networkSpecificB2} |
      facilityIEHandlingPackage{networkSpecificB1} |
      genericDisconnectResourcePackage{networkSpecificB1, networkSpecificB2} |
      nonAssistedConnectionEstablishmentPackage{networkSpecificB1,
                                               networkSpecificB2} |
      signallingControlPackage{networkSpecificB1, networkSpecificB2} |
      specializedResourceControlPackage{networkSpecificB1, networkSpecificB2,
                                       networkSpecificB3} |
      scriptControlPackage{networkSpecificB1, networkSpecificB2} |
      messageControlPackage{networkSpecificB1, networkSpecificB2,
                           networkSpecificB3} |
      ssfCallProcessingPackage{networkSpecificB1, networkSpecificB2} |
      statusReportingPackage{networkSpecificB1, networkSpecificB2} |
      timerPackage{networkSpecificB1, networkSpecificB2} |
      trafficManagementPackage{networkSpecificB1, networkSpecificB2} |
      uSIHandlingPackage{networkSpecificB1, networkSpecificB2} |
      scfCallInitiationPackage{networkSpecificB1, networkSpecificB2} |
      triggerCallManagementPackage{networkSpecificB1, networkSpecificB2}}
  ID                     id-inSsfToScfGeneric
}

inSsfToScfDpSpecific CONTRACT ::= {
  -- dialogue initiated by SSF with DP Specific Iniltial Operations
  --The inSsfToScfDpSpecific contract expresses the form of the service in which the SSF,
  -- a ROS-object of class ssf, initiates the DP specific triggering approach contract. 
  --A ROS-object of class scf, responds to this contract.
  INITIATOR CONSUMER OF
    {activityTestPackage |
      advancedBCPDPPackage{networkSpecificB1, networkSpecificB2} |
      basicBCPDPPackage{networkSpecificB1, networkSpecificB2} |
      exceptionInformPackage{networkSpecificB2}}
  RESPONDER CONSUMER OF
    {activityTestPackage |
      assistConnectionEstablishmentPackage{networkSpecificB1,
                                          networkSpecificB2} |
      billingPackage{networkSpecificB2} |
      callHandlingPackage{networkSpecificB2} |
      callReportPackage{networkSpecificB1, networkSpecificB2} |
      cancelPackage{networkSpecificB2} |
      chargingEventHandlingPackage{networkSpecificB1, networkSpecificB2} |
      chargingPackage{networkSpecificB1, networkSpecificB2} |
      connectPackage{networkSpecificB1, networkSpecificB2} |
      cphResponsePackage{networkSpecificB1, networkSpecificB2} |
      dpSpecificEventHandlingPackage{networkSpecificB1, networkSpecificB2} |
      facilityIEHandlingPackage{networkSpecificB1} |
      genericDisconnectResourcePackage{networkSpecificB1, networkSpecificB2} |
      nonAssistedConnectionEstablishmentPackage{networkSpecificB1,
                                               networkSpecificB2} |
      signallingControlPackage{networkSpecificB1, networkSpecificB2} |
      specializedResourceControlPackage{networkSpecificB1, networkSpecificB2,
                                       networkSpecificB3} |
      scriptControlPackage{networkSpecificB1, networkSpecificB2} |
      messageControlPackage{networkSpecificB1, networkSpecificB2,
                           networkSpecificB3} |
      ssfCallProcessingPackage{networkSpecificB1, networkSpecificB2} |
      statusReportingPackage{networkSpecificB1, networkSpecificB2} |
      timerPackage{networkSpecificB1, networkSpecificB2} |
      trafficManagementPackage{networkSpecificB1, networkSpecificB2} |
      uSIHandlingPackage{networkSpecificB1, networkSpecificB2} |
      scfCallInitiationPackage{networkSpecificB1, networkSpecificB2}}
  ID                     id-inSsfToScfDpSpecific
}

inAssistHandoffSsfToScf CONTRACT ::= {
  -- dialogue initiated by SSF with AssistRequestInstructions
  --The inAssistHandoffSsfToScf contract expresses the form of the service in which the SSF,
  -- a ROS-object of class ssf, initiates the Assist or Hand-off contract. 
  --A ROS-object of class scf, responds to this contract.
  INITIATOR CONSUMER OF
    {activityTestPackage |
      srf-scfActivationOfAssistPackage{networkSpecificB1, networkSpecificB2}}
  RESPONDER CONSUMER OF
    {activityTestPackage | billingPackage{networkSpecificB2} |
      callHandlingPackage{networkSpecificB2} | cancelPackage{networkSpecificB2}
      | chargingPackage{networkSpecificB1, networkSpecificB2} |
      signallingControlPackage{networkSpecificB1, networkSpecificB2} |
      genericDisconnectResourcePackage{networkSpecificB1, networkSpecificB2} |
      nonAssistedConnectionEstablishmentPackage{networkSpecificB1,
                                               networkSpecificB2} |
      specializedResourceControlPackage{networkSpecificB1, networkSpecificB2,
                                       networkSpecificB3} |
      scriptControlPackage{networkSpecificB1, networkSpecificB2} |
      messageControlPackage{networkSpecificB1, networkSpecificB2,
                           networkSpecificB3} |
      statusReportingPackage{networkSpecificB1, networkSpecificB2} |
      timerPackage{networkSpecificB1, networkSpecificB2}}
  ID                     id-inAssistHandoffSsfToScf
}

inScfToSsfGeneric CONTRACT ::= {
  --dialogue initiated by SCF with InitiateCallAttempt or CreateCallSegmentAssociation , Generic Case
  --The inScfToSsfGeneric contract expresses the form of the service in which the SCF, 
  --a ROS-object of class scf, initiates the generic messaging approach for the SCF 
  --Initiate Call Attempt contract. A ROS-object of class ssf, responds to this contract.
  INITIATOR CONSUMER OF
    {activityTestPackage |
      assistConnectionEstablishmentPackage{networkSpecificB1,
                                          networkSpecificB2} |
      bcsmEventHandlingPackage{networkSpecificB1, networkSpecificB2} |
      billingPackage{networkSpecificB2} |
      callHandlingPackage{networkSpecificB2} |
      callReportPackage{networkSpecificB1, networkSpecificB2} |
      cancelPackage{networkSpecificB2} |
      chargingEventHandlingPackage{networkSpecificB1, networkSpecificB2} |
      chargingPackage{networkSpecificB1, networkSpecificB2} |
      connectPackage{networkSpecificB1, networkSpecificB2} |
      cphResponsePackage{networkSpecificB1, networkSpecificB2} |
      facilityIEHandlingPackage{networkSpecificB1} |
      genericDisconnectResourcePackage{networkSpecificB1, networkSpecificB2} |
      nonAssistedConnectionEstablishmentPackage{networkSpecificB1,
                                               networkSpecificB2} |
      scfCallInitiationPackage{networkSpecificB1, networkSpecificB2} |
      signallingControlPackage{networkSpecificB1, networkSpecificB2} |
      specializedResourceControlPackage{networkSpecificB1, networkSpecificB2,
                                       networkSpecificB3} |
      scriptControlPackage{networkSpecificB1, networkSpecificB2} |
      messageControlPackage{networkSpecificB1, networkSpecificB2,
                           networkSpecificB3} |
      ssfCallProcessingPackage{networkSpecificB1, networkSpecificB2} |
      statusReportingPackage{networkSpecificB1, networkSpecificB2} |
      timerPackage{networkSpecificB1, networkSpecificB2} |
      uSIHandlingPackage{networkSpecificB1, networkSpecificB2} |
      scfCallInitiationPackage{networkSpecificB1, networkSpecificB2} |
      triggerCallManagementPackage{networkSpecificB1, networkSpecificB2}}
  RESPONDER CONSUMER OF
    {activityTestPackage | exceptionInformPackage{networkSpecificB2}}
  ID                     id-inScfToSsfGeneric
}

inScfToSsfDpSpecific CONTRACT ::= {
  -- dialogue initiated by SCF with InitiateCallAttempt, DP Specific Case
  --The inScfToSsfDpSpecific contract expresses the form of the service in which the SCF,
  -- a ROS-object of class scf, initiates the DP specific messaging approach for the SCF
  -- Initiate Call Attempt contract. A ROS-object of class ssf, responds to this contract.
  INITIATOR CONSUMER OF
    {activityTestPackage |
      assistConnectionEstablishmentPackage{networkSpecificB1,
                                          networkSpecificB2} |
      billingPackage{networkSpecificB2} |
      callHandlingPackage{networkSpecificB2} |
      callReportPackage{networkSpecificB1, networkSpecificB2} |
      cancelPackage{networkSpecificB2} |
      chargingEventHandlingPackage{networkSpecificB1, networkSpecificB2} |
      chargingPackage{networkSpecificB1, networkSpecificB2} |
      connectPackage{networkSpecificB1, networkSpecificB2} |
      cphResponsePackage{networkSpecificB1, networkSpecificB2} |
      dpSpecificEventHandlingPackage{networkSpecificB1, networkSpecificB2} |
      facilityIEHandlingPackage{networkSpecificB1} |
      genericDisconnectResourcePackage{networkSpecificB1, networkSpecificB2} |
      nonAssistedConnectionEstablishmentPackage{networkSpecificB1,
                                               networkSpecificB2} |
      scfCallInitiationPackage{networkSpecificB1, networkSpecificB2} |
      signallingControlPackage{networkSpecificB1, networkSpecificB2} |
      specializedResourceControlPackage{networkSpecificB1, networkSpecificB2,
                                       networkSpecificB3} |
      scriptControlPackage{networkSpecificB1, networkSpecificB2} |
      messageControlPackage{networkSpecificB1, networkSpecificB2,
                           networkSpecificB3} |
      ssfCallProcessingPackage{networkSpecificB1, networkSpecificB2} |
      statusReportingPackage{networkSpecificB1, networkSpecificB2} |
      timerPackage{networkSpecificB1, networkSpecificB2} |
      uSIHandlingPackage{networkSpecificB1, networkSpecificB2} |
      scfCallInitiationPackage{networkSpecificB1, networkSpecificB2}}
  RESPONDER CONSUMER OF
    {activityTestPackage | exceptionInformPackage{networkSpecificB2}}
  ID                     id-inScfToSsfDpSpecific
}

inScfToSsfINTrafficManagement CONTRACT ::= {
  -- dialogue initiated by SCF with CallGap
  --The inScfToSsfINTrafficManagement contract expresses the form of the service in 
  --which the SCF, a ROS-object of class scf, initiates the IN Traffic Management related contract.
  -- A ROS-object of class ssf, responds to this contract.
  INITIATOR CONSUMER OF
    {iNTrafficManagementPackage
       {networkSpecificB1,
        networkSpecificB2,
        networkSpecificB3}}
  ID                     id-inScfToSsfINTrafficManagement
}

inScfToSsfTrafficManagement CONTRACT ::= {
  -- dialogue initiated by SCF with Call Filtering
  --The inScfToSsfTrafficManagement contract expresses the form of the service in 
  --which the SCF, a ROS-object of class scf, initiates the Traffic Management related contract.
  -- A ROS-object of class ssf, responds to this contract.
  INITIATOR CONSUMER OF
    {trafficManagementPackage  {networkSpecificB1,
                                networkSpecificB2}}
  ID                     id-inScfToSsfTrafficManagement
}

inScfToSsfServiceManagement CONTRACT ::= {
  -- dialogue initiated by SCF with ActivateServiceFiltering
  --The inScfToSsfServiceManagement contract expresses the form of the service
  -- in which the SCF, a ROS-object of class scf, initiates the Service Management related contract.
  -- A ROS-object of class ssf, in the context of a separate contract, responds to this initiation.
  INITIATOR CONSUMER OF
    {serviceManagementActivatePackage
       {networkSpecificB1,
        networkSpecificB2,
        networkSpecificB3}}
  ID                     id-inScfToSsfServiceManagement
}

inSsfToScfServiceManagement CONTRACT ::= {
  -- dialogue initiated/ended by SSF with ServiceFilteringResponse
  --The inSsfToScfServiceManagement contract expresses the form of the service in 
  --which the SSF, a ROS-object of class ssf, initiates the Service Management related contract
  -- for reporting Service Management results. 
  INITIATOR CONSUMER OF
    {serviceManagementResponsePackage  {networkSpecificB1,
                                        networkSpecificB2}}
  ID                     id-inSsfToScfServiceManagement
}

inScfToSsfStatusReporting CONTRACT ::= {
  -- dialogue initiated by SCF with StatusReporting Operations
  --The inScfToSsfStatusReporting contract expresses the form of the service 
  --in which the SCF, a ROS-object of class scf, initiates the Status Reporting related contract. 
  --A ROS-object of class ssf, responds to this contract.
  INITIATOR CONSUMER OF
    {statusReportingPackage  {networkSpecificB1,
                              networkSpecificB2}}
  ID                     id-inScfToSsfStatusReporting
}

inScfToSsfTriggerManagement CONTRACT ::= {
  -- dialogue initiated by SCF with the trigger management operations CreateOrRemoveTriggerData or ManageTriggerData
  --The inScfToSsfTriggerManagement contract expresses the form of the service in which the SCF,
  -- a ROS-object of class scf, initiates the Trigger Management related contract
  -- A ROS-object of class ssf, in the context of a separate contract, responds to this initiation.
  INITIATOR CONSUMER OF
    {triggerManagementPackage
       {networkSpecificB1,
        networkSpecificB2,
        networkSpecificB3}}
  ID                     id-inScfToSsfTriggerManagement
}

inScfToSsfRouteMonitoring CONTRACT ::= {
  -- dialogue initiated by SCF with MonitorRouteRequest
  --The inScfToSsfRouteMonitoring contract expresses the form of the service in which the SCF,
  -- a ROS-object of class scf, initiates the route monitoring related contract
  -- A ROS-object of class ssf, in the context of a separate contract, responds to this initiation.
  INITIATOR CONSUMER OF
    {monitorRoutePackage  {networkSpecificB1,
                           networkSpecificB2}}
  ID                     id-inScfToSsfRouteMonitoring
}

inSsfToScfRouteMonitoring CONTRACT ::= {
  -- dialogue initiated by SSF with MonitorRouteResponse
  --The inSsfToScfRouteMonitoring contract expresses the form of the service in which the SSF,
  -- a ROS-Object of class ssf responds to a MonitorRouteRequest
  INITIATOR CONSUMER OF
    {monitorRoutePackage  {networkSpecificB1,
                           networkSpecificB2}}
  ID                     id-inSsfToScfRouteMonitoring
}

-- Packages 
scfActivationPackage{B1:b1, B2:b2} OPERATION-PACKAGE ::= {
  CONSUMER INVOKES  {initialDP{b1, b2}}
  ID                id-package-scfActivation
}

basicBCPDPPackage{B1:b1, B2:b2} OPERATION-PACKAGE ::= {
  CONSUMER INVOKES
    {originationAttemptAuthorized{b1, b2} | collectedInformation{b1, b2} |
      analysedInformation{b1, b2} | routeSelectFailure{b1, b2} |
      facilitySelectedAndAvailable{b1, b2} | oAbandon{b1, b2} |
      originationAttempt{b1, b2} | terminationAttempt{b1, b2} |
      oCalledPartyBusy{b1, b2} | oNoAnswer{b1, b2} | oAnswer{b1, b2} |
      oDisconnect{b1, b2} | termAttemptAuthorized{b1, b2} | tBusy{b1, b2} |
      tNoAnswer{b1, b2} | tAnswer{b1, b2} | tDisconnect{b1, b2}}
  ID                id-package-basicBCPDP
}

advancedBCPDPPackage{B1:b1, B2:b2} OPERATION-PACKAGE ::= {
  CONSUMER INVOKES
    {oMidCall{b1, b2} | oSuspended{b1, b2} | tMidCall{b1, b2} |
      tSuspended{b1, b2}}
  ID                id-package-advancedBCPDP
}

srf-scfActivationOfAssistPackage{B1:b1, B2:b2} OPERATION-PACKAGE ::= 
{
  CONSUMER INVOKES  {assistRequestInstructions{b1, b2}}
  ID                id-package-srf-scfActivationOfAssist
}

assistConnectionEstablishmentPackage{B1:b1, B2:b2} OPERATION-PACKAGE ::= 
{
  CONSUMER INVOKES  {establishTemporaryConnection{b1, b2}}
  ID                id-package-assistConnectionEstablishment
}

genericDisconnectResourcePackage{B1:b1, B2:b2} OPERATION-PACKAGE ::= 
{
  CONSUMER INVOKES
    {disconnectForwardConnection |
      disconnectForwardConnectionWithArgument{b1, b2}}
  ID                id-package-genericDisconnectResource
}

nonAssistedConnectionEstablishmentPackage{B1:b1, B2:b2} OPERATION-PACKAGE ::= 
{
  CONSUMER INVOKES  {connectToResource{b1, b2}}
  ID                id-package-nonAssistedConnectionEstablishment
}

connectPackage{B1:b1, B2:b2} OPERATION-PACKAGE ::= {
  CONSUMER INVOKES  {connect{b1, b2}}
  ID                id-package-connect
}

callHandlingPackage{B2:b2} OPERATION-PACKAGE ::= {
  CONSUMER INVOKES  {holdCallInNetwork | releaseCall{b2}}
  ID                id-package-callHandling
}

bcsmEventHandlingPackage{B1:b1, B2:b2} OPERATION-PACKAGE ::= {
  CONSUMER INVOKES  {requestReportBCSMEvent{b1, b2}}
  SUPPLIER INVOKES  {eventReportBCSM{b1, b2}}
  ID                id-package-bcsmEventHandling
}

dpSpecificEventHandlingPackage{B1:b1, B2:b2} OPERATION-PACKAGE ::= {
  CONSUMER INVOKES  {requestReportBCSMEvent{b1, b2}}
  SUPPLIER INVOKES
    {originationAttemptAuthorized{b1, b2} | collectedInformation{b1, b2} |
      analysedInformation{b1, b2} | routeSelectFailure{b1, b2} |
      facilitySelectedAndAvailable{b1, b2} | oAbandon{b1, b2} |
      originationAttempt{b1, b2} | terminationAttempt{b1, b2} |
      oCalledPartyBusy{b1, b2} | oNoAnswer{b1, b2} | oAnswer{b1, b2} |
      oDisconnect{b1, b2} | termAttemptAuthorized{b1, b2} | tBusy{b1, b2} |
      tNoAnswer{b1, b2} | tAnswer{b1, b2} | tDisconnect{b1, b2} |
      oMidCall{b1, b2} | oSuspended{b1, b2} | tMidCall{b1, b2} |
      tSuspended{b1, b2}}
  ID                id-package-dpSpecificEventHandling
}

chargingEventHandlingPackage{B1:b1, B2:b2} OPERATION-PACKAGE ::= {
  CONSUMER INVOKES  {requestNotificationChargingEvent{b2}}
  SUPPLIER INVOKES  {eventNotificationCharging{b1, b2}}
  ID                id-package-chargingEventHandling
}

ssfCallProcessingPackage{B1:b1, B2:b2} OPERATION-PACKAGE ::= {
  CONSUMER INVOKES
    {collectInformation{b1, b2} | analyseInformation{b1, b2} |
      authorizeTermination{b1, b2} | selectRoute{b1, b2} |
      selectFacility{b1, b2} | continue}
  ID                id-package-ssfCallProcessing
}

scfCallInitiationPackage{B1:b1, B2:b2} OPERATION-PACKAGE ::= {
  CONSUMER INVOKES  {initiateCallAttempt{b1, b2}}
  ID                id-package-scfCallInitiation
}

timerPackage{B1:b1, B2:b2} OPERATION-PACKAGE ::= {
  CONSUMER INVOKES  {resetTimer{b1, b2}}
  ID                id-package-timer
}

billingPackage{B2:b2} OPERATION-PACKAGE ::= {
  CONSUMER INVOKES  {furnishChargingInformation{b2}}
  ID                id-package-billing
}

chargingPackage{B1:b1, B2:b2} OPERATION-PACKAGE ::= {
  CONSUMER INVOKES  {applyCharging{b1, b2}}
  SUPPLIER INVOKES  {applyChargingReport{b2}}
  ID                id-package-charging
}

iNTrafficManagementPackage{B1:b1, B2:b2, B3:b3} OPERATION-PACKAGE ::= 
{
  CONSUMER INVOKES  {callGap{b1, b2, b3}}
  ID                id-package-iNTrafficManagement
}

trafficManagementPackage{B1:b1, B2:b2} OPERATION-PACKAGE ::= {
  CONSUMER INVOKES  {callFiltering{b1, b2}}
  ID                id-package-trafficManagement
}

serviceManagementActivatePackage{B1:b1, B2:b2, B3:b3} OPERATION-PACKAGE ::= 
{
  CONSUMER INVOKES  {activateServiceFiltering{b1, b2, b3}}
  ID                id-package-serviceManagementActivate
}

serviceManagementResponsePackage{B1:b1, B2:b2} OPERATION-PACKAGE ::= 
{
  CONSUMER INVOKES  {serviceFilteringResponse{b1, b2}}
  ID                id-package-serviceManagementResponse
}

callReportPackage{B1:b1, B2:b2} OPERATION-PACKAGE ::= {
  CONSUMER INVOKES  {callInformationRequest{b1, b2}}
  SUPPLIER INVOKES  {callInformationReport{b1, b2}}
  ID                id-package-callReport
}

signallingControlPackage{B1:b1, B2:b2} OPERATION-PACKAGE ::= {
  CONSUMER INVOKES  {sendChargingInformation{b1, b2}}
  ID                id-package-signallingControl
}

activityTestPackage OPERATION-PACKAGE ::= {
  CONSUMER INVOKES  {activityTest}
  ID                id-package-activityTest
}

statusReportingPackage{B1:b1, B2:b2} OPERATION-PACKAGE ::= {
  CONSUMER INVOKES
    {cancelStatusReportRequest{b1, b2} | requestCurrentStatusReport{b1, b2} |
      requestEveryStatusChangeReport{b1, b2} |
      requestFirstStatusMatchReport{b1, b2}}
  SUPPLIER INVOKES  {statusReport{b1, b2}}
  ID                id-package-statusReporting
}

cancelPackage{B2:b2} OPERATION-PACKAGE ::= {
  CONSUMER INVOKES  {cancel{b2}}
  ID                id-package-cancel
}

cphResponsePackage{B1:b1, B2:b2} OPERATION-PACKAGE ::= {
  CONSUMER INVOKES
    {continueWithArgument{b1, b2} | disconnectLeg{b1, b2} |
      mergeCallSegments{b1, b2} | moveCallSegments{b1, b2} | moveLeg{b1, b2} |
      createCallSegmentAssociation{b1, b2} | reconnect{b1, b2} |
      splitLeg{b1, b2}}
  ID                id-package-cphResponse
}

exceptionInformPackage{B2:b2} OPERATION-PACKAGE ::= {
  CONSUMER INVOKES  {entityReleased{b2}}
  ID                id-package-entityReleased
}

triggerCallManagementPackage{B1:b1, B2:b2} OPERATION-PACKAGE ::= {
  CONSUMER INVOKES  {setServiceProfile{b1, b2}}
  ID                id-package-triggerCallManagement
}

triggerManagementPackage{B1:b1, B2:b2, B3:b3} OPERATION-PACKAGE ::= {
  CONSUMER INVOKES
    {createOrRemoveTriggerData{b1, b2, b3} | manageTriggerData{b1, b2}}
  ID                id-package-triggerManagement
}

uSIHandlingPackage{B1:b1, B2:b2} OPERATION-PACKAGE ::= {
  CONSUMER INVOKES  {requestReportUTSI{b1, b2} | sendSTUI{b1, b2}}
  SUPPLIER INVOKES  {reportUTSI{b1, b2}}
  ID                id-package-uSIHandling
}

facilityIEHandlingPackage{B1:b1} OPERATION-PACKAGE ::= {
  CONSUMER INVOKES
    {requestReportFacilityEvent{b1} | sendFacilityInformation{b1}}
  SUPPLIER INVOKES  {eventReportFacility{b1}}
  ID                id-package-facilityIEHandling
}

monitorRoutePackage{B1:b1, B2:b2} OPERATION-PACKAGE ::= {
  CONSUMER INVOKES  {monitorRouteRequest{b1, b2}}
  SUPPLIER INVOKES  {monitorRouteReport{b1, b2}}
  ID                id-package-monitorRoute
}

-- Abstract Syntaxes 
ssf-scfGenericAbstractSyntax ABSTRACT-SYNTAX ::= {
  GenericSSF-SCF-PDUs
  IDENTIFIED BY  id-as-ssf-scfGenericAS
}

GenericSSF-SCF-PDUs ::=
  TCMessage{{SsfToScfGenericInvokable}, {SsfToScfGenericReturnable}}

SsfToScfGenericInvokable OPERATION ::=
  {activateServiceFiltering{networkSpecificB1, networkSpecificB2,
                           networkSpecificB3} | activityTest |
   applyCharging{networkSpecificB1, networkSpecificB2} |
   applyChargingReport{networkSpecificB2} |
   callInformationReport{networkSpecificB1, networkSpecificB2} |
   callInformationRequest{networkSpecificB1, networkSpecificB2} |
   cancel{networkSpecificB2} |
   cancelStatusReportRequest{networkSpecificB1, networkSpecificB2} |
   collectInformation{networkSpecificB1, networkSpecificB2} |
   connect{networkSpecificB1, networkSpecificB2} |
   connectToResource{networkSpecificB1, networkSpecificB2} |
   createCallSegmentAssociation{networkSpecificB1, networkSpecificB2} |
   disconnectForwardConnection |
   disconnectForwardConnectionWithArgument{networkSpecificB1,
                                          networkSpecificB2} |
   disconnectLeg{networkSpecificB1, networkSpecificB2} |
   entityReleased{networkSpecificB2} |
   establishTemporaryConnection{networkSpecificB1, networkSpecificB2} |
   eventNotificationCharging{networkSpecificB1, networkSpecificB2} |
   eventReportBCSM{networkSpecificB1, networkSpecificB2} |
   eventReportFacility{networkSpecificB1} |
   furnishChargingInformation{networkSpecificB2} | holdCallInNetwork |
   initialDP{networkSpecificB1, networkSpecificB2} |
   mergeCallSegments{networkSpecificB1, networkSpecificB2} |
   moveCallSegments{networkSpecificB1, networkSpecificB2} |
   moveLeg{networkSpecificB1, networkSpecificB2} |
   reconnect{networkSpecificB1, networkSpecificB2} |
   releaseCall{networkSpecificB2} |
   reportUTSI{networkSpecificB1, networkSpecificB2} |
   requestCurrentStatusReport{networkSpecificB1, networkSpecificB2} |
   requestEveryStatusChangeReport{networkSpecificB1, networkSpecificB2} |
   requestFirstStatusMatchReport{networkSpecificB1, networkSpecificB2} |
   requestNotificationChargingEvent{networkSpecificB2} |
   requestReportBCSMEvent{networkSpecificB1, networkSpecificB2} |
   requestReportFacilityEvent{networkSpecificB1} |
   requestReportUTSI{networkSpecificB1, networkSpecificB2} |
   resetTimer{networkSpecificB1, networkSpecificB2} |
   sendChargingInformation{networkSpecificB1, networkSpecificB2} |
   sendFacilityInformation{networkSpecificB1} |
   sendSTUI{networkSpecificB1, networkSpecificB2} |
   serviceFilteringResponse{networkSpecificB1, networkSpecificB2} |
   setServiceProfile{networkSpecificB1, networkSpecificB2} |
   splitLeg{networkSpecificB1, networkSpecificB2} |
   statusReport{networkSpecificB1, networkSpecificB2} |
   playAnnouncement{networkSpecificB1, networkSpecificB2, networkSpecificB3} |
   promptAndCollectUserInformation{networkSpecificB1, networkSpecificB2,
                                  networkSpecificB3} |
   scriptClose{networkSpecificB1, networkSpecificB2} |
   scriptEvent{networkSpecificB1, networkSpecificB2} |
   scriptInformation{networkSpecificB1, networkSpecificB2} |
   scriptRun{networkSpecificB1, networkSpecificB2} | specializedResourceReport
   |
   promptAndReceiveMessage{networkSpecificB1, networkSpecificB2,
                          networkSpecificB3}}

SsfToScfGenericReturnable OPERATION ::=
  {activateServiceFiltering{networkSpecificB1, networkSpecificB2,
                           networkSpecificB3} | activityTest |
   applyCharging{networkSpecificB1, networkSpecificB2} |
   applyChargingReport{networkSpecificB2} |
   callGap{networkSpecificB1, networkSpecificB2, networkSpecificB3} |
   callInformationRequest{networkSpecificB1, networkSpecificB2} |
   cancel{networkSpecificB2} |
   cancelStatusReportRequest{networkSpecificB1, networkSpecificB2} |
   collectInformation{networkSpecificB1, networkSpecificB2} |
   connect{networkSpecificB1, networkSpecificB2} |
   connectToResource{networkSpecificB1, networkSpecificB2} | continue |
   continueWithArgument{networkSpecificB1, networkSpecificB2} |
   createCallSegmentAssociation{networkSpecificB1, networkSpecificB2} |
   disconnectForwardConnection |
   disconnectForwardConnectionWithArgument{networkSpecificB1,
                                          networkSpecificB2} |
   disconnectLeg{networkSpecificB1, networkSpecificB2} |
   establishTemporaryConnection{networkSpecificB1, networkSpecificB2} |
   furnishChargingInformation{networkSpecificB2} | holdCallInNetwork |
   initialDP{networkSpecificB1, networkSpecificB2} |
   mergeCallSegments{networkSpecificB1, networkSpecificB2} |
   moveCallSegments{networkSpecificB1, networkSpecificB2} |
   moveLeg{networkSpecificB1, networkSpecificB2} |
   reconnect{networkSpecificB1, networkSpecificB2} |
   releaseCall{networkSpecificB2} |
   requestCurrentStatusReport{networkSpecificB1, networkSpecificB2} |
   requestEveryStatusChangeReport{networkSpecificB1, networkSpecificB2} |
   requestFirstStatusMatchReport{networkSpecificB1, networkSpecificB2} |
   requestNotificationChargingEvent{networkSpecificB2} |
   requestReportBCSMEvent{networkSpecificB1, networkSpecificB2} |
   requestReportFacilityEvent{networkSpecificB1} |
   requestReportUTSI{networkSpecificB1, networkSpecificB2} |
   resetTimer{networkSpecificB1, networkSpecificB2} |
   sendChargingInformation{networkSpecificB1, networkSpecificB2} |
   sendFacilityInformation{networkSpecificB1} |
   sendSTUI{networkSpecificB1, networkSpecificB2} |
   setServiceProfile{networkSpecificB1, networkSpecificB2} |
   splitLeg{networkSpecificB1, networkSpecificB2} |
   playAnnouncement{networkSpecificB1, networkSpecificB2, networkSpecificB3} |
   promptAndCollectUserInformation{networkSpecificB1, networkSpecificB2,
                                  networkSpecificB3} |
   scriptClose{networkSpecificB1, networkSpecificB2} |
   scriptInformation{networkSpecificB1, networkSpecificB2} |
   scriptRun{networkSpecificB1, networkSpecificB2} |
   promptAndReceiveMessage{networkSpecificB1, networkSpecificB2,
                          networkSpecificB3}}

ssf-scfDpSpecificAbstractSyntax ABSTRACT-SYNTAX ::= {
  DpSpecificSSF-SCF-PDUs
  IDENTIFIED BY  id-as-ssf-scfDpSpecificAS
}

DpSpecificSSF-SCF-PDUs ::=
  TCMessage{{SsfToScfDpSpecificInvokable}, {SsfToScfDpSpecificReturnable}}

SsfToScfDpSpecificInvokable OPERATION ::=
  {activateServiceFiltering{networkSpecificB1, networkSpecificB2,
                           networkSpecificB3} | activityTest |
   analyseInformation{networkSpecificB1, networkSpecificB2} |
   analysedInformation{networkSpecificB1, networkSpecificB2} |
   applyCharging{networkSpecificB1, networkSpecificB2} |
   applyChargingReport{networkSpecificB2} |
   assistRequestInstructions{networkSpecificB1, networkSpecificB2} |
   callInformationReport{networkSpecificB1, networkSpecificB2} |
   callInformationRequest{networkSpecificB1, networkSpecificB2} |
   cancel{networkSpecificB2} |
   cancelStatusReportRequest{networkSpecificB1, networkSpecificB2} |
   collectedInformation{networkSpecificB1, networkSpecificB2} |
   collectInformation{networkSpecificB1, networkSpecificB2} |
   connect{networkSpecificB1, networkSpecificB2} |
   connectToResource{networkSpecificB1, networkSpecificB2} |
   createCallSegmentAssociation{networkSpecificB1, networkSpecificB2} |
   disconnectForwardConnection |
   disconnectForwardConnectionWithArgument{networkSpecificB1,
                                          networkSpecificB2} |
   disconnectLeg{networkSpecificB1, networkSpecificB2} |
   entityReleased{networkSpecificB2} |
   establishTemporaryConnection{networkSpecificB1, networkSpecificB2} |
   eventNotificationCharging{networkSpecificB1, networkSpecificB2} |
   eventReportFacility{networkSpecificB1} |
   furnishChargingInformation{networkSpecificB2} | holdCallInNetwork |
   initiateCallAttempt{networkSpecificB1, networkSpecificB2} |
   mergeCallSegments{networkSpecificB1, networkSpecificB2} |
   moveCallSegments{networkSpecificB1, networkSpecificB2} |
   moveLeg{networkSpecificB1, networkSpecificB2} |
   oAbandon{networkSpecificB1, networkSpecificB2} |
   oAnswer{networkSpecificB1, networkSpecificB2} |
   oCalledPartyBusy{networkSpecificB1, networkSpecificB2} |
   oDisconnect{networkSpecificB1, networkSpecificB2} |
   oMidCall{networkSpecificB1, networkSpecificB2} |
   oNoAnswer{networkSpecificB1, networkSpecificB2} |
   originationAttemptAuthorized{networkSpecificB1, networkSpecificB2} |
   reconnect{networkSpecificB1, networkSpecificB2} |
   releaseCall{networkSpecificB2} |
   reportUTSI{networkSpecificB1, networkSpecificB2} |
   requestCurrentStatusReport{networkSpecificB1, networkSpecificB2} |
   requestEveryStatusChangeReport{networkSpecificB1, networkSpecificB2} |
   requestFirstStatusMatchReport{networkSpecificB1, networkSpecificB2} |
   requestNotificationChargingEvent{networkSpecificB2} |
   requestReportBCSMEvent{networkSpecificB1, networkSpecificB2} |
   requestReportFacilityEvent{networkSpecificB1} |
   requestReportUTSI{networkSpecificB1, networkSpecificB2} |
   resetTimer{networkSpecificB1, networkSpecificB2} |
   routeSelectFailure{networkSpecificB1, networkSpecificB2} |
   selectFacility{networkSpecificB1, networkSpecificB2} |
   selectRoute{networkSpecificB1, networkSpecificB2} |
   sendChargingInformation{networkSpecificB1, networkSpecificB2} |
   sendFacilityInformation{networkSpecificB1} |
   sendSTUI{networkSpecificB1, networkSpecificB2} |
   serviceFilteringResponse{networkSpecificB1, networkSpecificB2} |
   setServiceProfile{networkSpecificB1, networkSpecificB2} |
   splitLeg{networkSpecificB1, networkSpecificB2} |
   statusReport{networkSpecificB1, networkSpecificB2} |
   tAnswer{networkSpecificB1, networkSpecificB2} |
   tBusy{networkSpecificB1, networkSpecificB2} |
   tDisconnect{networkSpecificB1, networkSpecificB2} |
   termAttemptAuthorized{networkSpecificB1, networkSpecificB2} |
   tMidCall{networkSpecificB1, networkSpecificB2} |
   tNoAnswer{networkSpecificB1, networkSpecificB2} |
   playAnnouncement{networkSpecificB1, networkSpecificB2, networkSpecificB3} |
   promptAndCollectUserInformation{networkSpecificB1, networkSpecificB2,
                                  networkSpecificB3} |
   scriptClose{networkSpecificB1, networkSpecificB2} |
   scriptEvent{networkSpecificB1, networkSpecificB2} |
   scriptInformation{networkSpecificB1, networkSpecificB2} |
   scriptRun{networkSpecificB1, networkSpecificB2} | specializedResourceReport
   |
   promptAndReceiveMessage{networkSpecificB1, networkSpecificB2,
                          networkSpecificB3}}

SsfToScfDpSpecificReturnable OPERATION ::=
  {activateServiceFiltering{networkSpecificB1, networkSpecificB2,
                           networkSpecificB3} | activityTest |
   analyseInformation{networkSpecificB1, networkSpecificB2} |
   analysedInformation{networkSpecificB1, networkSpecificB2} |
   applyCharging{networkSpecificB1, networkSpecificB2} |
   applyChargingReport{networkSpecificB2} |
   assistRequestInstructions{networkSpecificB1, networkSpecificB2} |
   callGap{networkSpecificB1, networkSpecificB2, networkSpecificB3} |
   callInformationRequest{networkSpecificB1, networkSpecificB2} |
   cancel{networkSpecificB2} |
   cancelStatusReportRequest{networkSpecificB1, networkSpecificB2} |
   collectedInformation{networkSpecificB1, networkSpecificB2} |
   collectInformation{networkSpecificB1, networkSpecificB2} |
   connect{networkSpecificB1, networkSpecificB2} |
   connectToResource{networkSpecificB1, networkSpecificB2} | continue |
   continueWithArgument{networkSpecificB1, networkSpecificB2} |
   createCallSegmentAssociation{networkSpecificB1, networkSpecificB2} |
   disconnectForwardConnection |
   disconnectForwardConnectionWithArgument{networkSpecificB1,
                                          networkSpecificB2} |
   disconnectLeg{networkSpecificB1, networkSpecificB2} |
   establishTemporaryConnection{networkSpecificB1, networkSpecificB2} |
   furnishChargingInformation{networkSpecificB2} | holdCallInNetwork |
   initiateCallAttempt{networkSpecificB1, networkSpecificB2} |
   mergeCallSegments{networkSpecificB1, networkSpecificB2} |
   moveCallSegments{networkSpecificB1, networkSpecificB2} |
   moveLeg{networkSpecificB1, networkSpecificB2} |
   oAbandon{networkSpecificB1, networkSpecificB2} |
   oAnswer{networkSpecificB1, networkSpecificB2} |
   oCalledPartyBusy{networkSpecificB1, networkSpecificB2} |
   oDisconnect{networkSpecificB1, networkSpecificB2} |
   oMidCall{networkSpecificB1, networkSpecificB2} |
   oNoAnswer{networkSpecificB1, networkSpecificB2} |
   originationAttemptAuthorized{networkSpecificB1, networkSpecificB2} |
   reconnect{networkSpecificB1, networkSpecificB2} |
   releaseCall{networkSpecificB2} |
   requestCurrentStatusReport{networkSpecificB1, networkSpecificB2} |
   requestEveryStatusChangeReport{networkSpecificB1, networkSpecificB2} |
   requestFirstStatusMatchReport{networkSpecificB1, networkSpecificB2} |
   requestNotificationChargingEvent{networkSpecificB2} |
   requestReportBCSMEvent{networkSpecificB1, networkSpecificB2} |
   requestReportFacilityEvent{networkSpecificB1} |
   requestReportUTSI{networkSpecificB1, networkSpecificB2} |
   resetTimer{networkSpecificB1, networkSpecificB2} |
   routeSelectFailure{networkSpecificB1, networkSpecificB2} |
   selectFacility{networkSpecificB1, networkSpecificB2} |
   selectRoute{networkSpecificB1, networkSpecificB2} |
   sendChargingInformation{networkSpecificB1, networkSpecificB2} |
   sendFacilityInformation{networkSpecificB1} |
   sendSTUI{networkSpecificB1, networkSpecificB2} |
   setServiceProfile{networkSpecificB1, networkSpecificB2} |
   splitLeg{networkSpecificB1, networkSpecificB2} |
   tAnswer{networkSpecificB1, networkSpecificB2} |
   tBusy{networkSpecificB1, networkSpecificB2} |
   tDisconnect{networkSpecificB1, networkSpecificB2} |
   termAttemptAuthorized{networkSpecificB1, networkSpecificB2} |
   tMidCall{networkSpecificB1, networkSpecificB2} |
   tNoAnswer{networkSpecificB1, networkSpecificB2} |
   playAnnouncement{networkSpecificB1, networkSpecificB2, networkSpecificB3} |
   promptAndCollectUserInformation{networkSpecificB1, networkSpecificB2,
                                  networkSpecificB3} |
   scriptClose{networkSpecificB1, networkSpecificB2} |
   scriptInformation{networkSpecificB1, networkSpecificB2} |
   scriptRun{networkSpecificB1, networkSpecificB2} |
   promptAndReceiveMessage{networkSpecificB1, networkSpecificB2,
                          networkSpecificB3}}

assistHandoff-ssf-scfAbstractSyntax ABSTRACT-SYNTAX ::= {
  AssistHandoffSSF-SCF-PDUs
  IDENTIFIED BY  id-as-assistHandoff-ssf-scfAS
}

AssistHandoffSSF-SCF-PDUs ::=
  TCMessage
    {{AssistHandoffSsfToScfInvokable}, {AssistHandoffSsfToScfReturnable}}

AssistHandoffSsfToScfInvokable OPERATION ::=
  {activityTest | applyCharging{networkSpecificB1, networkSpecificB2} |
   applyChargingReport{networkSpecificB2} |
   assistRequestInstructions{networkSpecificB1, networkSpecificB2} |
   cancel{networkSpecificB2} |
   cancelStatusReportRequest{networkSpecificB1, networkSpecificB2} |
   connectToResource{networkSpecificB1, networkSpecificB2} |
   disconnectForwardConnection |
   disconnectForwardConnectionWithArgument{networkSpecificB1,
                                          networkSpecificB2} |
   furnishChargingInformation{networkSpecificB2} | holdCallInNetwork |
   playAnnouncement{networkSpecificB1, networkSpecificB2, networkSpecificB3} |
   promptAndCollectUserInformation{networkSpecificB1, networkSpecificB2,
                                  networkSpecificB3} |
   requestCurrentStatusReport{networkSpecificB1, networkSpecificB2} |
   requestEveryStatusChangeReport{networkSpecificB1, networkSpecificB2} |
   requestFirstStatusMatchReport{networkSpecificB1, networkSpecificB2} |
   resetTimer{networkSpecificB1, networkSpecificB2} |
   statusReport{networkSpecificB1, networkSpecificB2} |
   scriptClose{networkSpecificB1, networkSpecificB2} |
   scriptEvent{networkSpecificB1, networkSpecificB2} |
   scriptInformation{networkSpecificB1, networkSpecificB2} |
   scriptRun{networkSpecificB1, networkSpecificB2} |
   sendChargingInformation{networkSpecificB1, networkSpecificB2} |
   specializedResourceReport |
   promptAndReceiveMessage{networkSpecificB1, networkSpecificB2,
                          networkSpecificB3}}

AssistHandoffSsfToScfReturnable OPERATION ::=
  {activityTest | applyCharging{networkSpecificB1, networkSpecificB2} |
   applyChargingReport{networkSpecificB2} |
   assistRequestInstructions{networkSpecificB1, networkSpecificB2} |
   cancel{networkSpecificB2} |
   cancelStatusReportRequest{networkSpecificB1, networkSpecificB2} |
   connectToResource{networkSpecificB1, networkSpecificB2} |
   disconnectForwardConnection |
   disconnectForwardConnectionWithArgument{networkSpecificB1,
                                          networkSpecificB2} |
   furnishChargingInformation{networkSpecificB2} | holdCallInNetwork |
   playAnnouncement{networkSpecificB1, networkSpecificB2, networkSpecificB3} |
   promptAndCollectUserInformation{networkSpecificB1, networkSpecificB2,
                                  networkSpecificB3} |
   requestCurrentStatusReport{networkSpecificB1, networkSpecificB2} |
   requestEveryStatusChangeReport{networkSpecificB1, networkSpecificB2} |
   requestFirstStatusMatchReport{networkSpecificB1, networkSpecificB2} |
   resetTimer{networkSpecificB1, networkSpecificB2} |
   scriptClose{networkSpecificB1, networkSpecificB2} |
   scriptInformation{networkSpecificB1, networkSpecificB2} |
   scriptRun{networkSpecificB1, networkSpecificB2} |
   promptAndReceiveMessage{networkSpecificB1, networkSpecificB2,
                          networkSpecificB3}}

scf-ssfGenericAbstractSyntax ABSTRACT-SYNTAX ::= {
  GenericSCF-SSF-PDUs
  IDENTIFIED BY  id-as-scf-ssfGenericAS
}

GenericSCF-SSF-PDUs ::=
  TCMessage{{ScfToSsfGenericInvokable}, {ScfToSsfGenericReturnable}}

ScfToSsfGenericInvokable OPERATION ::=
  {activateServiceFiltering{networkSpecificB1, networkSpecificB2,
                           networkSpecificB3} | activityTest |
   applyCharging{networkSpecificB1, networkSpecificB2} |
   applyChargingReport{networkSpecificB2} |
   callInformationRequest{networkSpecificB1, networkSpecificB2} |
   cancel{networkSpecificB2} |
   cancelStatusReportRequest{networkSpecificB1, networkSpecificB2} |
   collectInformation{networkSpecificB1, networkSpecificB2} |
   connect{networkSpecificB1, networkSpecificB2} |
   connectToResource{networkSpecificB1, networkSpecificB2} | continue |
   continueWithArgument{networkSpecificB1, networkSpecificB2} |
   createCallSegmentAssociation{networkSpecificB1, networkSpecificB2} |
   disconnectForwardConnection |
   disconnectForwardConnectionWithArgument{networkSpecificB1,
                                          networkSpecificB2} |
   disconnectLeg{networkSpecificB1, networkSpecificB2} |
   establishTemporaryConnection{networkSpecificB1, networkSpecificB2} |
   furnishChargingInformation{networkSpecificB2} | holdCallInNetwork |
   initiateCallAttempt{networkSpecificB1, networkSpecificB2} |
   mergeCallSegments{networkSpecificB1, networkSpecificB2} |
   moveCallSegments{networkSpecificB1, networkSpecificB2} |
   moveLeg{networkSpecificB1, networkSpecificB2} |
   releaseCall{networkSpecificB2} |
   reconnect{networkSpecificB1, networkSpecificB2} |
   requestCurrentStatusReport{networkSpecificB1, networkSpecificB2} |
   requestEveryStatusChangeReport{networkSpecificB1, networkSpecificB2} |
   requestFirstStatusMatchReport{networkSpecificB1, networkSpecificB2} |
   requestNotificationChargingEvent{networkSpecificB2} |
   requestReportBCSMEvent{networkSpecificB1, networkSpecificB2} |
   requestReportFacilityEvent{networkSpecificB1} |
   requestReportUTSI{networkSpecificB1, networkSpecificB2} |
   resetTimer{networkSpecificB1, networkSpecificB2} |
   sendChargingInformation{networkSpecificB1, networkSpecificB2} |
   sendFacilityInformation{networkSpecificB1} |
   sendSTUI{networkSpecificB1, networkSpecificB2} |
   setServiceProfile{networkSpecificB1, networkSpecificB2} |
   splitLeg{networkSpecificB1, networkSpecificB2} |
   playAnnouncement{networkSpecificB1, networkSpecificB2, networkSpecificB3} |
   promptAndCollectUserInformation{networkSpecificB1, networkSpecificB2,
                                  networkSpecificB3} |
   scriptClose{networkSpecificB1, networkSpecificB2} |
   scriptInformation{networkSpecificB1, networkSpecificB2} |
   scriptRun{networkSpecificB1, networkSpecificB2} |
   promptAndReceiveMessage{networkSpecificB1, networkSpecificB2,
                          networkSpecificB3}}

ScfToSsfGenericReturnable OPERATION ::=
  {activateServiceFiltering{networkSpecificB1, networkSpecificB2,
                           networkSpecificB3} | activityTest |
   applyCharging{networkSpecificB1, networkSpecificB2} |
   applyChargingReport{networkSpecificB2} |
   callInformationReport{networkSpecificB1, networkSpecificB2} |
   callInformationRequest{networkSpecificB1, networkSpecificB2} |
   cancel{networkSpecificB2} |
   cancelStatusReportRequest{networkSpecificB1, networkSpecificB2} |
   collectInformation{networkSpecificB1, networkSpecificB2} |
   connect{networkSpecificB1, networkSpecificB2} |
   connectToResource{networkSpecificB1, networkSpecificB2} |
   createCallSegmentAssociation{networkSpecificB1, networkSpecificB2} |
   disconnectForwardConnection |
   disconnectForwardConnectionWithArgument{networkSpecificB1,
                                          networkSpecificB2} |
   disconnectLeg{networkSpecificB1, networkSpecificB2} |
   entityReleased{networkSpecificB2} |
   establishTemporaryConnection{networkSpecificB1, networkSpecificB2} |
   eventNotificationCharging{networkSpecificB1, networkSpecificB2} |
   resetTimer{networkSpecificB1, networkSpecificB2} |
   eventReportBCSM{networkSpecificB1, networkSpecificB2} |
   eventReportFacility{networkSpecificB1} |
   furnishChargingInformation{networkSpecificB2} | holdCallInNetwork |
   initiateCallAttempt{networkSpecificB1, networkSpecificB2} |
   mergeCallSegments{networkSpecificB1, networkSpecificB2} |
   moveCallSegments{networkSpecificB1, networkSpecificB2} |
   moveLeg{networkSpecificB1, networkSpecificB2} |
   reconnect{networkSpecificB1, networkSpecificB2} |
   reportUTSI{networkSpecificB1, networkSpecificB2} |
   requestCurrentStatusReport{networkSpecificB1, networkSpecificB2} |
   requestEveryStatusChangeReport{networkSpecificB1, networkSpecificB2} |
   requestFirstStatusMatchReport{networkSpecificB1, networkSpecificB2} |
   requestNotificationChargingEvent{networkSpecificB2} |
   requestReportBCSMEvent{networkSpecificB1, networkSpecificB2} |
   requestReportFacilityEvent{networkSpecificB1} |
   requestReportUTSI{networkSpecificB1, networkSpecificB2} |
   sendChargingInformation{networkSpecificB1, networkSpecificB2} |
   sendFacilityInformation{networkSpecificB1} |
   sendSTUI{networkSpecificB1, networkSpecificB2} |
   serviceFilteringResponse{networkSpecificB1, networkSpecificB2} |
   setServiceProfile{networkSpecificB1, networkSpecificB2} |
   splitLeg{networkSpecificB1, networkSpecificB2} |
   statusReport{networkSpecificB1, networkSpecificB2} |
   playAnnouncement{networkSpecificB1, networkSpecificB2, networkSpecificB3} |
   promptAndCollectUserInformation{networkSpecificB1, networkSpecificB2,
                                  networkSpecificB3} |
   scriptClose{networkSpecificB1, networkSpecificB2} |
   scriptEvent{networkSpecificB1, networkSpecificB2} |
   scriptInformation{networkSpecificB1, networkSpecificB2} |
   scriptRun{networkSpecificB1, networkSpecificB2} | specializedResourceReport
   |
   promptAndReceiveMessage{networkSpecificB1, networkSpecificB2,
                          networkSpecificB3}}

scf-ssfDpSpecificAbstractSyntax ABSTRACT-SYNTAX ::= {
  DpSpecificSCF-SSF-PDUs
  IDENTIFIED BY  id-as-scf-ssfDpSpecificAS
}

DpSpecificSCF-SSF-PDUs ::=
  TCMessage{{ScfToSsfDpSpecificInvokable}, {ScfToSsfDpSpecificReturnable}}

ScfToSsfDpSpecificInvokable OPERATION ::=
  {activateServiceFiltering{networkSpecificB1, networkSpecificB2,
                           networkSpecificB3} | activityTest |
   analyseInformation{networkSpecificB1, networkSpecificB2} |
   analysedInformation{networkSpecificB1, networkSpecificB2} |
   applyCharging{networkSpecificB1, networkSpecificB2} |
   applyChargingReport{networkSpecificB2} |
   callInformationRequest{networkSpecificB1, networkSpecificB2} |
   cancel{networkSpecificB2} |
   cancelStatusReportRequest{networkSpecificB1, networkSpecificB2} |
   collectedInformation{networkSpecificB1, networkSpecificB2} |
   collectInformation{networkSpecificB1, networkSpecificB2} |
   connect{networkSpecificB1, networkSpecificB2} |
   connectToResource{networkSpecificB1, networkSpecificB2} | continue |
   continueWithArgument{networkSpecificB1, networkSpecificB2} |
   createCallSegmentAssociation{networkSpecificB1, networkSpecificB2} |
   createOrRemoveTriggerData{networkSpecificB1, networkSpecificB2,
                            networkSpecificB3} | disconnectForwardConnection |
   disconnectForwardConnectionWithArgument{networkSpecificB1,
                                          networkSpecificB2} |
   disconnectLeg{networkSpecificB1, networkSpecificB2} |
   establishTemporaryConnection{networkSpecificB1, networkSpecificB2} |
   furnishChargingInformation{networkSpecificB2} | holdCallInNetwork |
   initiateCallAttempt{networkSpecificB1, networkSpecificB2} |
   manageTriggerData{networkSpecificB1, networkSpecificB2} |
   mergeCallSegments{networkSpecificB1, networkSpecificB2} |
   moveCallSegments{networkSpecificB1, networkSpecificB2} |
   moveLeg{networkSpecificB1, networkSpecificB2} |
   oAbandon{networkSpecificB1, networkSpecificB2} |
   oAnswer{networkSpecificB1, networkSpecificB2} |
   oCalledPartyBusy{networkSpecificB1, networkSpecificB2} |
   oDisconnect{networkSpecificB1, networkSpecificB2} |
   oMidCall{networkSpecificB1, networkSpecificB2} |
   oNoAnswer{networkSpecificB1, networkSpecificB2} |
   originationAttemptAuthorized{networkSpecificB1, networkSpecificB2} |
   reconnect{networkSpecificB1, networkSpecificB2} |
   releaseCall{networkSpecificB2} |
   requestCurrentStatusReport{networkSpecificB1, networkSpecificB2} |
   requestEveryStatusChangeReport{networkSpecificB1, networkSpecificB2} |
   requestFirstStatusMatchReport{networkSpecificB1, networkSpecificB2} |
   requestNotificationChargingEvent{networkSpecificB2} |
   requestReportBCSMEvent{networkSpecificB1, networkSpecificB2} |
   requestReportFacilityEvent{networkSpecificB1} |
   requestReportUTSI{networkSpecificB1, networkSpecificB2} |
   resetTimer{networkSpecificB1, networkSpecificB2} |
   routeSelectFailure{networkSpecificB1, networkSpecificB2} |
   selectFacility{networkSpecificB1, networkSpecificB2} |
   selectRoute{networkSpecificB1, networkSpecificB2} |
   sendChargingInformation{networkSpecificB1, networkSpecificB2} |
   sendFacilityInformation{networkSpecificB1} |
   sendSTUI{networkSpecificB1, networkSpecificB2} |
   setServiceProfile{networkSpecificB1, networkSpecificB2} |
   splitLeg{networkSpecificB1, networkSpecificB2} |
   tAnswer{networkSpecificB1, networkSpecificB2} |
   tBusy{networkSpecificB1, networkSpecificB2} |
   tDisconnect{networkSpecificB1, networkSpecificB2} |
   termAttemptAuthorized{networkSpecificB1, networkSpecificB2} |
   tMidCall{networkSpecificB1, networkSpecificB2} |
   tNoAnswer{networkSpecificB1, networkSpecificB2} |
   playAnnouncement{networkSpecificB1, networkSpecificB2, networkSpecificB3} |
   promptAndCollectUserInformation{networkSpecificB1, networkSpecificB2,
                                  networkSpecificB3} |
   scriptClose{networkSpecificB1, networkSpecificB2} |
   scriptInformation{networkSpecificB1, networkSpecificB2} |
   scriptRun{networkSpecificB1, networkSpecificB2} |
   promptAndReceiveMessage{networkSpecificB1, networkSpecificB2,
                          networkSpecificB3}}

ScfToSsfDpSpecificReturnable OPERATION ::=
  {activateServiceFiltering{networkSpecificB1, networkSpecificB2,
                           networkSpecificB3} | activityTest |
   analyseInformation{networkSpecificB1, networkSpecificB2} |
   analysedInformation{networkSpecificB1, networkSpecificB2} |
   applyCharging{networkSpecificB1, networkSpecificB2} |
   applyChargingReport{networkSpecificB2} |
   callInformationReport{networkSpecificB1, networkSpecificB2} |
   callInformationRequest{networkSpecificB1, networkSpecificB2} |
   cancel{networkSpecificB2} |
   cancelStatusReportRequest{networkSpecificB1, networkSpecificB2} |
   collectedInformation{networkSpecificB1, networkSpecificB2} |
   collectInformation{networkSpecificB1, networkSpecificB2} |
   connect{networkSpecificB1, networkSpecificB2} |
   connectToResource{networkSpecificB1, networkSpecificB2} |
   createCallSegmentAssociation{networkSpecificB1, networkSpecificB2} |
   disconnectForwardConnection |
   disconnectForwardConnectionWithArgument{networkSpecificB1,
                                          networkSpecificB2} |
   disconnectLeg{networkSpecificB1, networkSpecificB2} |
   entityReleased{networkSpecificB2} |
   establishTemporaryConnection{networkSpecificB1, networkSpecificB2} |
   eventNotificationCharging{networkSpecificB1, networkSpecificB2} |
   eventReportFacility{networkSpecificB1} |
   furnishChargingInformation{networkSpecificB2} | holdCallInNetwork |
   initiateCallAttempt{networkSpecificB1, networkSpecificB2} |
   initiateCallAttempt{networkSpecificB1, networkSpecificB2} |
   mergeCallSegments{networkSpecificB1, networkSpecificB2} |
   moveCallSegments{networkSpecificB1, networkSpecificB2} |
   moveLeg{networkSpecificB1, networkSpecificB2} |
   oAnswer{networkSpecificB1, networkSpecificB2} |
   oCalledPartyBusy{networkSpecificB1, networkSpecificB2} |
   oDisconnect{networkSpecificB1, networkSpecificB2} |
   oMidCall{networkSpecificB1, networkSpecificB2} |
   oAbandon{networkSpecificB1, networkSpecificB2} |
   oNoAnswer{networkSpecificB1, networkSpecificB2} |
   originationAttemptAuthorized{networkSpecificB1, networkSpecificB2} |
   reconnect{networkSpecificB1, networkSpecificB2} |
   reportUTSI{networkSpecificB1, networkSpecificB2} |
   requestCurrentStatusReport{networkSpecificB1, networkSpecificB2} |
   requestEveryStatusChangeReport{networkSpecificB1, networkSpecificB2} |
   requestFirstStatusMatchReport{networkSpecificB1, networkSpecificB2} |
   requestNotificationChargingEvent{networkSpecificB2} |
   requestReportBCSMEvent{networkSpecificB1, networkSpecificB2} |
   requestReportFacilityEvent{networkSpecificB1} |
   requestReportUTSI{networkSpecificB1, networkSpecificB2} |
   resetTimer{networkSpecificB1, networkSpecificB2} |
   routeSelectFailure{networkSpecificB1, networkSpecificB2} |
   selectFacility{networkSpecificB1, networkSpecificB2} |
   selectRoute{networkSpecificB1, networkSpecificB2} |
   sendChargingInformation{networkSpecificB1, networkSpecificB2} |
   sendFacilityInformation{networkSpecificB1} |
   sendSTUI{networkSpecificB1, networkSpecificB2} |
   serviceFilteringResponse{networkSpecificB1, networkSpecificB2} |
   setServiceProfile{networkSpecificB1, networkSpecificB2} |
   splitLeg{networkSpecificB1, networkSpecificB2} |
   statusReport{networkSpecificB1, networkSpecificB2} |
   tAnswer{networkSpecificB1, networkSpecificB2} |
   tBusy{networkSpecificB1, networkSpecificB2} |
   tDisconnect{networkSpecificB1, networkSpecificB2} |
   termAttemptAuthorized{networkSpecificB1, networkSpecificB2} |
   tMidCall{networkSpecificB1, networkSpecificB2} |
   tNoAnswer{networkSpecificB1, networkSpecificB2} |
   playAnnouncement{networkSpecificB1, networkSpecificB2, networkSpecificB3} |
   promptAndCollectUserInformation{networkSpecificB1, networkSpecificB2,
                                  networkSpecificB3} |
   scriptClose{networkSpecificB1, networkSpecificB2} |
   scriptEvent{networkSpecificB1, networkSpecificB2} |
   scriptInformation{networkSpecificB1, networkSpecificB2} |
   scriptRun{networkSpecificB1, networkSpecificB2} | specializedResourceReport
   |
   promptAndReceiveMessage{networkSpecificB1, networkSpecificB2,
                          networkSpecificB3}}

scf-ssfINTrafficManagementAbstractSyntax ABSTRACT-SYNTAX ::= {
  INTrafficManagementSCF-SSF-PDUs
  IDENTIFIED BY  id-as-scf-ssfINTrafficManagementAS
}

INTrafficManagementSCF-SSF-PDUs ::=
  TCMessage{{ScfToSsfINTrafficManagementInvokable}, {EmptyReturnable}}

ScfToSsfINTrafficManagementInvokable OPERATION ::=
  {callGap{networkSpecificB1, networkSpecificB2, networkSpecificB3}}

scf-ssfTrafficManagementAbstractSyntax ABSTRACT-SYNTAX ::= {
  TrafficManagementSCF-SSF-PDUs
  IDENTIFIED BY  id-as-scf-ssfTrafficManagementAS
}

TrafficManagementSCF-SSF-PDUs ::=
  TCMessage{{ScfToSsfTrafficManagementInvokable}, {EmptyReturnable}}

ScfToSsfTrafficManagementInvokable OPERATION ::=
  {callFiltering{networkSpecificB1, networkSpecificB2}}

scf-ssfServiceManagementAbstractSyntax ABSTRACT-SYNTAX ::= {
  ServiceManagementSCF-SSF-PDUs
  IDENTIFIED BY  id-as-scf-ssfServiceManagementAS
}

ServiceManagementSCF-SSF-PDUs ::=
  TCMessage
    {{ScfToSsfServiceManagementInvokable},
    {ScfToSsfServiceManagementReturnable}}

ScfToSsfServiceManagementInvokable OPERATION ::=
  {activateServiceFiltering{networkSpecificB1, networkSpecificB2,
                           networkSpecificB3}}

ScfToSsfServiceManagementReturnable OPERATION ::=
  {activateServiceFiltering{networkSpecificB1, networkSpecificB2,
                           networkSpecificB3}}

ssf-scfServiceManagementAbstractSyntax ABSTRACT-SYNTAX ::= {
  ServiceManagementSSF-SCF-PDUs
  IDENTIFIED BY  id-as-ssf-scfServiceManagementAS
}

ServiceManagementSSF-SCF-PDUs ::=
  TCMessage{{SsfToScfServiceManagementInvokable}, {EmptyReturnable}}

SsfToScfServiceManagementInvokable OPERATION ::=
  {serviceFilteringResponse{networkSpecificB1, networkSpecificB2}}

scf-ssfStatusReportingAbstractSyntax ABSTRACT-SYNTAX ::= {
  StatusReportingSCF-SSF-PDUs
  IDENTIFIED BY  id-as-scf-ssfStatusReportingAS
}

StatusReportingSCF-SSF-PDUs ::=
  TCMessage
    {{ScfToSsfStatusReportingInvokable}, {ScfToSsfStatusReportingReturnable}}

ScfToSsfStatusReportingInvokable OPERATION ::=
  {cancelStatusReportRequest{networkSpecificB1, networkSpecificB2} |
   requestCurrentStatusReport{networkSpecificB1, networkSpecificB2} |
   requestEveryStatusChangeReport{networkSpecificB1, networkSpecificB2} |
   requestFirstStatusMatchReport{networkSpecificB1, networkSpecificB2}}

ScfToSsfStatusReportingReturnable OPERATION ::=
  {cancelStatusReportRequest{networkSpecificB1, networkSpecificB2} |
   requestCurrentStatusReport{networkSpecificB1, networkSpecificB2} |
   requestEveryStatusChangeReport{networkSpecificB1, networkSpecificB2} |
   requestFirstStatusMatchReport{networkSpecificB1, networkSpecificB2} |
   statusReport{networkSpecificB1, networkSpecificB2}}

scf-ssfTriggerManagementAbstractSyntax ABSTRACT-SYNTAX ::= {
  TriggerManagementSCF-SSF-PDUs
  IDENTIFIED BY  id-as-scf-ssfTriggerManagementAS
}

TriggerManagementSCF-SSF-PDUs ::=
  TCMessage
    {{ScfToSsfTriggerManagementInvokable},
    {ScfToSsfTriggerManagementReturnable}}

ScfToSsfTriggerManagementInvokable OPERATION ::=
  {createOrRemoveTriggerData{networkSpecificB1, networkSpecificB2,
                            networkSpecificB3} |
   manageTriggerData{networkSpecificB1, networkSpecificB2}}

ScfToSsfTriggerManagementReturnable OPERATION ::=
  {createOrRemoveTriggerData{networkSpecificB1, networkSpecificB2,
                            networkSpecificB3} |
   manageTriggerData{networkSpecificB1, networkSpecificB2}}

scf-ssfRouteMonitoringAbstractSyntax ABSTRACT-SYNTAX ::= {
  RouteMonitoringSCF-SSF-PDUs
  IDENTIFIED BY  id-as-scf-ssfRouteMonitoringAS
}

RouteMonitoringSCF-SSF-PDUs ::=
  TCMessage
    {{ScfToSsfRouteMonitoringInvokable}, {ScfToSsfRouteMonitoringReturnable}}

ScfToSsfRouteMonitoringInvokable OPERATION ::=
  {monitorRouteRequest{networkSpecificB1, networkSpecificB2}}

ScfToSsfRouteMonitoringReturnable OPERATION ::=
  {monitorRouteRequest{networkSpecificB1, networkSpecificB2}}

ssf-scfRouteMonitoringAbstractSyntax ABSTRACT-SYNTAX ::= {
  RouteMonitoringSSF-SCF-PDUs
  IDENTIFIED BY  id-as-ssf-scfRouteMonitoringAS
}

RouteMonitoringSSF-SCF-PDUs ::=
  TCMessage{{SsfToScfRouteMonitoringInvokable}, {EmptyReturnable}}

SsfToScfRouteMonitoringInvokable OPERATION ::=
  {monitorRouteReport{networkSpecificB1, networkSpecificB2}}

END

-- Generated by Asnp, the ASN.1 pretty-printer of France Telecom R&D

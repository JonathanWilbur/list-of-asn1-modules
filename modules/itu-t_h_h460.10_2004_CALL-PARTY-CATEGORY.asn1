CALL-PARTY-CATEGORY (H.460.10:03/2004)


-- Module CALL-PARTY-CATEGORY (H.460.10:03/2004)
-- See also ITU-T H.460.10 (03/2004)
-- See also the index of all ASN.1 assignments needed in this document

CALL-PARTY-CATEGORY DEFINITIONS AUTOMATIC TAGS ::=
BEGIN

CallPartyCategoryInfo ::= SEQUENCE {
  callPartyCategory    CallPartyCategory OPTIONAL,
  originatingLineInfo  OriginatingLineInfo OPTIONAL,
  ...
}

CallPartyCategory ::= INTEGER(0..255)

OriginatingLineInfo ::= INTEGER(0..255)

END

-- Generated by Asnp, the ASN.1 pretty-printer of France Telecom R&D

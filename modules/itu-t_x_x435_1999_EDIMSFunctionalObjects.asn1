EDIMSFunctionalObjects (X.435:06/1999)


-- Module EDIMSFunctionalObjects (X.435:06/1999)
-- See also ITU-T X.435 (06/1999)
-- See also the index of all ASN.1 assignments needed in this document

EDIMSFunctionalObjects {joint-iso-itu-t mhs(6) edims(7) modules(0)
  functional-objects(1)} DEFINITIONS IMPLICIT TAGS ::=
BEGIN

--	Prologue
--	Exports everything
IMPORTS
  --	EDIMS Abstract Service
  origination, reception
    --==
    FROM EDIMSAbstractService {joint-iso-itu-t mhs(6) edims(7) modules(0)
      abstract-service(3)}
  --	EDIMS Object Identifiers
  id-ot-edimg-user, id-ot-edims
    --==
    FROM EDIMSObjectIdentifiers {joint-iso-itu-t mhs(6) edims(7) modules(0)
      object-identifiers(0) version(2)}
  --	Remote operations
  CONTRACT
    --==
    FROM Remote-Operations-Information-Objects {joint-iso-itu-t
      remote-operations(4) informationObjects(5) version1(0)}
  --	MTS Abstract Service
  MHS-OBJECT
    --==
    FROM MTSAbstractService {joint-iso-itu-t mhs(6) mts(3) modules(0)
      mts-abstract-service(1) version-1999(1)};

--	END imports
--	Primary Object Types
--	EDI User
edimg-user MHS-OBJECT ::= {
  INITIATES  {edims-access-contract}
  ID         id-ot-edimg-user
}

edims-access-contract CONTRACT ::= {
  INITIATOR CONSUMER OF  {origination | reception}
}

--	EDI Messaging System
edims MHS-OBJECT ::= {RESPONDS  {edims-access-contract}
                      ID        id-ot-edims
}

END --	of EDIMSFunctionalObjects

-- Generated by Asnp, the ASN.1 pretty-printer of France Telecom R&D

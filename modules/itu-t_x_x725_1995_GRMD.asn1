GRMD (X.725:11/1995)


-- Module GRMD (X.725:11/1995)
-- See also ITU-T X.725 (11/1995)
-- See also the index of all ASN.1 assignments needed in this document

GRMD {joint-iso-itu-t ms(9) smi(3) part7(7) asn1Module(2) 1} DEFINITIONS ::=
BEGIN

grm-Object OBJECT IDENTIFIER ::=
  {joint-iso-itu-t ms(9) smi(3) part7(7) managedObjectClass(3)}

grm-Package OBJECT IDENTIFIER ::=
  {joint-iso-itu-t ms(9) smi(3) part7(7) package(4)}

grm-Parameter OBJECT IDENTIFIER ::=
  {joint-iso-itu-t ms(9) smi(3) part7(7) parameter(5)}

grm-NameBinding OBJECT IDENTIFIER ::=
  {joint-iso-itu-t ms(9) smi(3) part7(7) nameBinding(6)}

grm-Attribute OBJECT IDENTIFIER ::=
  {joint-iso-itu-t ms(9) smi(3) part7(7) attribute(7)}

grm-RelationshipClass OBJECT IDENTIFIER ::=
  {joint-iso-itu-t ms(9) smi(3) part7(7) relationshipClass(11)}

grm-RelationshipMapping OBJECT IDENTIFIER ::=
  {joint-iso-itu-t ms(9) smi(3) part7(7) relationshipMapping(12)}

grm-RelationshipRole OBJECT IDENTIFIER ::=
  {joint-iso-itu-t ms(9) smi(3) part7(7) relationshipRole(13)}

END

-- Generated by Asnp, the ASN.1 pretty-printer of France Telecom R&D

QOS-MONITORING-REPORT (H.460.9:11/2002)


-- Module QOS-MONITORING-REPORT (H.460.9:11/2002)
-- See also ITU-T H.460.9 (11/2002)
-- See also the index of all ASN.1 assignments needed in this document

QOS-MONITORING-REPORT DEFINITIONS AUTOMATIC TAGS ::=
BEGIN

IMPORTS
  NonStandardParameter, TransportChannelInfo, CallIdentifier,
    CallReferenceValue, ConferenceIdentifier, BandWidth, GenericIdentifier
    FROM H323-MESSAGES;

EstimatedEnd2EndDelay ::= INTEGER(0..4294967295)

-- middle 32 bits of 64 bit NTP timestamp
CalculatedJitter ::= INTEGER(0..4294967295)

-- measured in timestamp units
Extension ::= SEQUENCE {
  extensionId       GenericIdentifier,
  extensionContent  OCTET STRING OPTIONAL,
  ...
}

RTCPMeasures ::= SEQUENCE {
  rtpAddress             TransportChannelInfo,
  rtcpAddress            TransportChannelInfo,
  sessionId              INTEGER(1..255),
  nonStandardData        NonStandardParameter OPTIONAL,
  mediaSenderMeasures
    SEQUENCE {worstEstimatedEnd2EndDelay  EstimatedEnd2EndDelay OPTIONAL,
              meanEstimatedEnd2EndDelay   EstimatedEnd2EndDelay OPTIONAL,
              ...} OPTIONAL,
  mediaReceiverMeasures
    SEQUENCE {cumulativeNumberOfPacketsLost  INTEGER(0..4294967295) OPTIONAL,
              packetLostRate                 INTEGER(0..65535) OPTIONAL,
              worstJitter                    CalculatedJitter OPTIONAL,
              estimatedThroughput            BandWidth OPTIONAL, -- in 100s of bits--
              fractionLostRate               INTEGER(0..65535) OPTIONAL,
              meanJitter                     CalculatedJitter OPTIONAL,
              ...} OPTIONAL,
  extensions             SEQUENCE OF Extension OPTIONAL,
  ...
}

PerCallQoSReport ::= SEQUENCE {
  nonStandardData     NonStandardParameter OPTIONAL,
  callReferenceValue  CallReferenceValue,
  conferenceID        ConferenceIdentifier,
  callIdentifier      CallIdentifier,
  mediaChannelsQoS    SEQUENCE OF RTCPMeasures OPTIONAL,
  -- one element per media channel
  extensions          SEQUENCE OF Extension OPTIONAL,
  ...
}

QosMonitoringReportData ::= CHOICE {
  periodic  PeriodicQoSMonReport, -- included in IRR messages
  final     FinalQosMonReport, -- included in DRQ/DCF message
  interGK   InterGKQosMonReport, -- included in usageIndication message
  ...
}

PeriodicQoSMonReport ::= SEQUENCE {
  perCallInfo  SEQUENCE OF PerCallQoSReport, -- one element per call
  extensions   SEQUENCE OF Extension OPTIONAL,
  ...
}

FinalQosMonReport ::= SEQUENCE {
  mediaInfo        SEQUENCE OF RTCPMeasures, -- one element per channel
  nonStandardData  NonStandardParameter OPTIONAL,
  extensions       SEQUENCE OF Extension OPTIONAL,
  ...
}

InterGKQosMonReport ::= SEQUENCE {
  mediaInfo        SEQUENCE OF RTCPMeasures, -- one element per channel
  nonStandardData  NonStandardParameter OPTIONAL,
  extensions       SEQUENCE OF Extension OPTIONAL,
  ...
}

--
-- H.460.9 Identifiers: 
--
qosMonitoringReportID GenericIdentifier ::=
  standard:9

qosMonitoringFinalOnly GenericIdentifier ::= standard:0

qosMonitoringReportData GenericIdentifier ::= standard:1

END -- of ASN.1

-- Generated by Asnp, the ASN.1 pretty-printer of France Telecom R&D

M3.asn: ITU-T X.683 (11/2008) -- ASN module extracted from ITU-T X.683 (11/2008)M3 DEFINITIONS AUTOMATIC TAGS ::= BEGIN
	IMPORTS T1 FROM  M1;
	T5 ::= T4{T1}
	T4{Y} ::= SEQUENCE {
	a	INTEGER,
	b	Y
}
END

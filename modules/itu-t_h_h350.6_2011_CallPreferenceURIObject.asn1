CallPreferenceURIObject (H.350.6:05/2011)


-- Module CallPreferenceURIObject (H.350.6:05/2011)
-- See also ITU-T H.350.6 (05/2011)
-- See also the index of all ASN.1 assignments needed in this document

CallPreferenceURIObject {itu-t(0) recommendation(0) h(8) 350 1 cr(1) 
  call(8) module(4)} DEFINITIONS ::=
BEGIN

-- callPreferenceURIObject Object Schema
-- Schema for representing a callPreferenceURIObject Object in an LDAP Directory
-- Abstract
-- This Recommendation defines the schema for representing callPreferenceURIObject 
-- object in an LDAP directory [LDAPv3].  It defines schema elements
-- to represent a callPreferenceURIObject object [callPreferenceURIObject].
--                     .1 = Communication related work
--                     .1.8 = callPreferenceURIObject
--                     .1.8.1 = attributes
--                     .1.8.2 = objectclass
--                     .1.8.3 = syntax
IMPORTS
  -- from Rec. ITU-T H.350
  h350-cr
    FROM CommURI {itu-t(0) recommendation(0) h(8) 350 1 cr(1) commURI(1)
      module(4)}
  -- from Rec. ITU-T X.501 | ISO/IEC 9594-2
  ATTRIBUTE, OBJECT-CLASS, top
    FROM InformationFramework {joint-iso-itu-t ds(5) module(1)
      informationFramework(1) 6}
  -- from Rec. ITU-T X.520 | ISO/IEC 9594-6
  UnboundedDirectoryString, caseExactMatch, caseExactSubstringsMatch
    FROM SelectedAttributeTypes {joint-iso-itu-t ds(5) module(1)
      selectedAttributeTypes(5) 6};

-- Attribute Type Definitions
--    The following attribute types are defined in this Recommendation:
--     callPreferenceURI
callPreferenceURI ATTRIBUTE ::= {
  WITH SYNTAX               UnboundedDirectoryString
  EQUALITY MATCHING RULE    caseExactMatch
  SUBSTRINGS MATCHING RULE  caseExactSubstringsMatch
  ID                        {at  1}
}

-- Object Class Definitions
--    The following object class is defined in this Recommendation:
-- 
--        callPreferenceURIObject
-- callPreferenceURIObject
callPreferenceURIObject OBJECT-CLASS ::= {
  SUBCLASS OF  {top}
  MAY CONTAIN  {callPreferenceURI}
  ID           {oc  1}
}

call-Id OBJECT IDENTIFIER ::= {h350-cr call-Id(8)}

at OBJECT IDENTIFIER ::= {call-Id at(1)}

oc OBJECT IDENTIFIER ::= {call-Id oc(2)}

END -- end of ASN.1

-- Generated by Asnp, the ASN.1 pretty-printer of France Telecom R&D

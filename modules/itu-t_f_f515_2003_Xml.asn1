Xml (F.515:04/2003)


-- Module Xml (F.515:04/2003)
-- See also ITU-T F.515 (04/2003)
-- See also the index of all ASN.1 assignments needed in this document

Xml DEFINITIONS AUTOMATIC TAGS ::=
BEGIN

IMPORTS
  AnyURI, NCName, Language
    FROM XSD; -- The XSD module is defined in the ASN.1 standards.

Lang ::= Language

Space ::= ENUMERATED {default, preserve}

Base ::= AnyURI

SpecialAttrs ::= SEQUENCE {
  base   Base OPTIONAL,
  lang   Lang OPTIONAL,
  space  Space OPTIONAL
}

/*

ENCODING-CONTROL XER
    ATTRIBUTE ALL IN SpecialAttrs, Space, Lang, Base
    TEXT Space

*/
END

-- Generated by Asnp, the ASN.1 pretty-printer of France Telecom R&D

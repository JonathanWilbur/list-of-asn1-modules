Reverse-Charging-Service-Private-Networks-Operation (Q.956.3:10/1995)


-- Module Reverse-Charging-Service-Private-Networks-Operation (Q.956.3:10/1995)
-- See also ITU-T Q.956.3 (10/1995)
-- See also the index of all ASN.1 assignments needed in this document

Reverse-Charging-Service-Private-Networks-Operation {itu-t recommendation 
  q 956 reverse-charging(3) private-networks-operation(2)} DEFINITIONS ::=
BEGIN

EXPORTS rEV-T-Status;

IMPORTS
  OPERATION, ERROR
    FROM Remote-Operations-Information-Objects {joint-iso-itu-t
      remote-operations(4) informationObjects(5) version1(0)};

rEV-T-Status OPERATION ::= {ARGUMENT  Status
                            CODE      local:62
}

Status ::= ENUMERATED {wholeCall(1), forTheRestOfTheCall(2)}

END -- of Reverse-Charging-Service-Private-Networks-Operation

-- Generated by Asnp, the ASN.1 pretty-printer of France Telecom R&D

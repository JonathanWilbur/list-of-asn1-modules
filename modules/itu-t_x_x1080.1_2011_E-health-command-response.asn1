E-health-command-response (X.1080.1:10/2011)


-- Module E-health-command-response (X.1080.1:10/2011)
-- See also ITU-T X.1080.1 (10/2011)
-- See also the index of all ASN.1 assignments needed in this document

E-health-command-response {joint-iso-itu-t(2) telebiometrics(42)
  e-health-protocol(3) modules(0) command-response(3) version1(1)} 
  "/Telebiometrics/E-Health_Protocol/Modules/Command-response/Version1"
  DEFINITIONS
AUTOMATIC TAGS ::=
BEGIN

IMPORTS
  EncryptionOptions, IntegrityOptions
    FROM E-health-setup {joint-iso-itu-t(2) telebiometrics(42)
      e-health-protocol(3) modules(0) set-up(1) version1(1)};

-- Type and CLASS definitions for CR interactive message sequences
CR-SEQUENCE ::= CLASS {
  &id                              OBJECT IDENTIFIER UNIQUE,
  &requirements                    ENUMERATED {none, with-2-way-voice,
                                                   with-reverse-video-and-2-way-voice,
                                                   with-2-way-video-and-voice},
  &voice-options                   OBJECT IDENTIFIER,
  &video-options                   OBJECT IDENTIFIER,
  &message-sequence-specification  UniversalString,
  &Interactive-Messages            INTERACTIVE-MESSAGE,
  &first                           INTERACTIVE-MESSAGE
}
WITH SYNTAX {
  INTERACTIVE-SESSION IDENTIFIED BY &id
  REQUIRING &requirements
  WITH VOICE OPTIONS &voice-options
  AND VIDEO OPTIONS &video-options
  SPECIFIED BY &message-sequence-specification
  USING &Interactive-Messages
  BEGINNING WITH &first
}

CR-Sequences CR-SEQUENCE ::=
  {...}

INTERACTIVE-MESSAGE ::= CLASS {
  &id                 INTEGER(0..MAX) UNIQUE,
  &direction          ENUMERATED {command, response},
  &Type               ,
  &expected-response  INTERACTIVE-MESSAGE OPTIONAL,
  -- only for a command
  &next               SEQUENCE OF INTERACTIVE-MESSAGE.&id OPTIONAL
}
WITH SYNTAX {
  STEP &id
  DIRECTION &direction
  USING &Type
  [RESPONSE &expected-response]
  [FOLLOWED BY &next]
}

Identified-Command-Response{INTERACTIVE-MESSAGE:Messages} ::= CHOICE {
  command
    SEQUENCE {message-id
                INTERACTIVE-MESSAGE.&id({Messages})
                  (CONSTRAINED BY {-- direction shall be command -- }),
              message-content
                INTERACTIVE-MESSAGE.&Type({Messages}{@.message-id})
  },
  response
    SEQUENCE {message-id
                INTERACTIVE-MESSAGE.&id({Messages})
                  (CONSTRAINED BY {-- id shall be equal to ---- expected-response of the command -- 
                     }),
              message-content
                INTERACTIVE-MESSAGE.&Type({Messages}{@.message-id})
  }
}

Command-Response ::= SEQUENCE {
  encryptionOptions  EncryptionOptions,
  integrityOptions   IntegrityOptions,
  content
    OCTET STRING
      (CONSTRAINED BY {-- encoding of an Identified-Command-Response value by the current ---- encoding rules followed by an encryption operation if --
         
         -- encryptionOptions is TRUE -- })
}

END

-- Generated by Asnp, the ASN.1 pretty-printer of France Telecom R&D

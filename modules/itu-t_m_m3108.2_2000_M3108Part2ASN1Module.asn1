M3108Part2ASN1Module (M.3108.2:02/2000)


-- Module M3108Part2ASN1Module (M.3108.2:02/2000)
-- See also ITU-T M.3108.2 (02/2000)
-- See also the index of all ASN.1 assignments needed in this document

M3108Part2ASN1Module {itu-t recommendation m lcs(3108) connectionManagement(2)
  informationModel(0) asn1Modules(2) asn1DefinedTypesModule(0)} DEFINITIONS
IMPLICIT TAGS ::=
BEGIN

--  EXPORTS Everything 
IMPORTS
  ObjectInstance
    FROM CMIP-1 {joint-iso-itu-t(2) ms(9) cmip(1) modules(0) protocol(3)}; -- IMPORTS End

-- Begin Registration Values
m3108Part2Identifier OBJECT IDENTIFIER ::=
  {itu-t recommendation m lcs(3108) connectionManagement(2) informationModel(0)
   asn1Modules(2) asn1DefinedTypesModule(0)}

m3108Part2ObjectClass OBJECT IDENTIFIER ::=
  {m3108Part2Identifier objectClass(3)}

m3108Part2Parameter OBJECT IDENTIFIER ::= {m3108Part2Identifier parameter(4)}

m3108Part2NameBinding OBJECT IDENTIFIER ::=
  {m3108Part2Identifier nameBinding(5)}

m3108Part2Attribute OBJECT IDENTIFIER ::= {m3108Part2Identifier attribute(6)}

-- End Registration Values
CreateCmLeasedCircuitServiceError ::= ENUMERATED {
  contractViolation(0), dedicatedResourceUnavailable(1), incompatibleSLCs(2),
  invalidSchedule(3), invalidServiceTerminationDate(4), invalidValue(5),
  nonExistentSAP(6), quantitySpecifiedOutOfRange(7),
  requestedBandwidthNotAvailable(8), requiredParameterNotAvailable(9),
  sharedResourcesUnavailable(10), specifiedLCSAlreadyExists(11),
  unknownServiceDescription(12), unknownServiceType(13), ...
  }

DedicatedOrShared ::= ENUMERATED {dedicated(1), shared(2), ...
                                  }

DeleteCmLeasedCircuitServiceError ::= ENUMERATED {
  alreadyDeleted(0), contractViolation(1), invalidCircuitNumber(2),
  unlockedAdministrativeState(3), ...
  }

InitiateLoopbackError ::= ENUMERATED {
  unavailableLCS(1), offDutyLCS(2), loopbackNotSupported(3), ...
  }

IdentifyLockedLCSError ::= ENUMERATED {
  administrativeStateUnlocked(0), nonExistentSAP(1), unknownServiceType(2), ...
  }

LeasedCircuitServicePtrList ::= SEQUENCE OF ObjectInstance

LinkEndCharacteristics ::= SEQUENCE {
  endID              [0]  GraphicString,
  loopbackSupported  [1]  BOOLEAN,
  ...
}

ListOfSLCsUsed ::= SEQUENCE OF ObjectInstance

LoopbackControl ::= SEQUENCE {
  status
    [0]  ENUMERATED {noLoopback(0), endALoopedBack(1), endBLoopedBack(2)},
  terminationTime  [1]  UTCTime,
  ...
}

ModifyLCSError ::= ENUMERATED {
  contractViolation(0), invalidAliasName(1), invalidCircuitNumber(2),
  invalidCPEType(3), invalidSchedule(4), invalidServiceTerminationDate(5),
  invalidValue(6), requestedBandwidthNotAvailable(7), resourceUnavailable(8),
  scheduleConflicts(9), ...
  }

RestrictionsOnSLC ::= SEQUENCE {
  restrictionId
    [0]  ENUMERATED {noRestrictions(1), protectedSLCsOnly(2),
                     protectedDedicatedSLCsOnly(3),
                     dedicatedSLCsOnlyWithProtectedSLCsPreferred(4),
                     dedicatedSLCsPreferredProtectedSLCsRequired(5),
                     dedicatedProtectedSLCsPreferred(6), ...
                     },
  restrictionText  [1]  GraphicString OPTIONAL,
  ...
}

SelectionPriority ::= INTEGER(1..10)

SlcEnds ::= SEQUENCE {
  endA  [0]  LinkEndCharacteristics,
  endB  [1]  LinkEndCharacteristics
}

TerminateLoopbackError ::= ENUMERATED {
  loopbackNotSet(0), loopbackNotSupported(1), ...
  }

END

-- Generated by Asnp, the ASN.1 pretty-printer of France Telecom R&D

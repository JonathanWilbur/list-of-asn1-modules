Remote-Operations-Information-Objects-extensions (Rec. X.881:07/1994)


-- Module Remote-Operations-Information-Objects-extensions (X.881:07/1994)
-- See also ITU-T X.881 (07/1994)
-- See also the index of all ASN.1 assignments needed in this Recommendation

Remote-Operations-Information-Objects-extensions {joint-iso-itu-t
  remote-operations(4) informationObjects-extensions(8) version1(0)}
DEFINITIONS ::=
BEGIN

-- exports everything
IMPORTS
  CONTRACT
    FROM Remote-Operations-Information-Objects {joint-iso-itu-t
      remote-operations(4) informationObjects(5) version1(0)};

APPLICATION-CONTEXT ::= CLASS {
  &amp;associationContract     CONTRACT,
  &amp;associationRealization  REALIZATION OPTIONAL,
  &amp;transferRealization     REALIZATION,
  &amp;AbstractSyntaxes        ABSTRACT-SYNTAX,
  &amp;applicationContextName  OBJECT IDENTIFIER UNIQUE
}
WITH SYNTAX {
  CONTRACT &amp;associationContract
  [ESTABLISHED BY &amp;associationRealization]
  INFORMATION TRANSFER BY &amp;transferRealization
  ABSTRACT SYNTAXES &amp;AbstractSyntaxes
  APPLICATION CONTEXT NAME &amp;applicationContextName
}

REALIZATION ::= TYPE-IDENTIFIER

-- information objects ABSTRACT-SYNTAX and TYPE-IDENTIFIER are defined in ITU-T Rec. X.681 |
-- ISO/IEC 8824-2
END -- end of the information-objects-extensions module

-- Generated by Asnp, the ASN.1 pretty-printer of France Telecom R&amp;D

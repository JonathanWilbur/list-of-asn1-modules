BIP-TCPIP (X.1083:11/2007)


-- Module BIP-TCPIP (X.1083:11/2007)
-- See also ITU-T X.1083 (11/2007)
-- See also the index of all ASN.1 assignments needed in this document

BIP-TCPIP {joint-iso-itu-t bip(41) modules(0) bip-tcpip(1) version1(1)}
DEFINITIONS AUTOMATIC TAGS ::=
BEGIN

IMPORTS
  BIPMessage
    FROM BIP {joint-iso-itu-t bip(41) modules(0) bip(0) version1(1)};

TCPIPBIPMessage ::= SEQUENCE {
  magicNumber  OCTET STRING(SIZE (4))('3AC49E70'H),
  version      INTEGER {version-1(1)}(0..255),
  content
    CHOICE {bIPMessage
              OCTET STRING(CONTAINING BIPMessage ENCODED BY basic-per-aligned),
            keepalive                          NULL,
            requestLinkChannelOnSpecifiedPort  INTEGER(0..65535),
            requestLinkChannel                 NULL}
}

basic-per-aligned OBJECT IDENTIFIER ::=
  {joint-iso-itu-t asn1(1) packed-encoding(3) basic(0) aligned(0)}

END

-- Generated by Asnp, the ASN.1 pretty-printer of France Telecom R&D

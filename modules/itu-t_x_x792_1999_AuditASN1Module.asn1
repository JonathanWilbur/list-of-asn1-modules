AuditASN1Module (X.792:03/1999)


-- Module AuditASN1Module (X.792:03/1999)
-- See also ITU-T X.792 (03/1999)
-- See also the index of all ASN.1 assignments needed in this document

AuditASN1Module {itu-t recommendation x(24) configAud(792) informationModel(0)
  asn1Modules(2) asn1DefinedTypeModules(0)} DEFINITIONS IMPLICIT TAGS ::=
BEGIN

-- EXPORTS everything
IMPORTS
  NameType
    FROM ASN1DefinedTypesModule {itu-t recommendation m gnm(3100)
      informationModel(0) asn1Modules(2) asn1DefinedTypesModule(0)};

configAuditSup OBJECT IDENTIFIER ::=
  {itu-t recommendation x configAud(792) informationModel(0)}

configAuditSupstandardSpecificExtension OBJECT IDENTIFIER ::=
  {configAuditSup standardSpecificExtension(0)}

configAuditSupMObjectClass OBJECT IDENTIFIER ::=
  {configAuditSup managedObjectClass(3)}

configAuditSupPackage OBJECT IDENTIFIER ::= {configAuditSup package(4)}

configAuditSupParameter OBJECT IDENTIFIER ::= {configAuditSup parameter(5)}

configAuditSupAttribute OBJECT IDENTIFIER ::= {configAuditSup attribute(7)}

configAuditSupNameBinding OBJECT IDENTIFIER ::= {configAuditSup nameBinding(6)}

configAuditSupAction OBJECT IDENTIFIER ::= {configAuditSup action(9)}

configAuditSupNotification OBJECT IDENTIFIER ::=
  {configAuditSup notification(10)}

-- Reserved arcs below configAuditSup are (8) for attribute groups
AuditInitiateInformation ::= SEQUENCE {
  classes
    SEQUENCE {include  CHOICE {all     NULL,
                               subset  SET OF OBJECT IDENTIFIER},
              exclude  CHOICE {none    NULL,
                               subset  SET OF OBJECT IDENTIFIER}},
  attributes
    SEQUENCE {include  CHOICE {all     NULL,
                               subset  SET OF OBJECT IDENTIFIER},
              exclude  CHOICE {none    NULL,
                               subset  SET OF OBJECT IDENTIFIER}}
}

AuditInitiateResult ::= ENUMERATED {
  started(0), auditAlreadyRunning(1), resourceLimit(2), notStartedOther(3)
}

AuditTerminateResult ::= ENUMERATED {
  terminated(0), noAuditRunning(1), couldNotTerminate(2)}

AuditResult ::= ENUMERATED {
  succeeded(0), partialSuccess(1), terminatedExternally(2),
  terminatedInternally(3), terminatedNoFileSpace(4)}

FileSuspect ::= BOOLEAN -- False means file is OK (not suspect)

OutputResult ::=
  SEQUENCE OF
    SEQUENCE {filename     GraphicString,
              fileSuspect  FileSuspect DEFAULT FALSE}

AuditReportInformation ::= SEQUENCE {
  result        AuditResult,
  outputResult  OutputResult OPTIONAL
}

Boolean ::= BOOLEAN

TimeStamp ::= CHOICE {neverRun  NULL,
                      run       GeneralizedTime
}

END -- of AuditASN1Module

-- Generated by Asnp, the ASN.1 pretty-printer of France Telecom R&D

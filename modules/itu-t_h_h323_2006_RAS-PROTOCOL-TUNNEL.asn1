RAS-PROTOCOL-TUNNEL (H.323:06/2006)


-- Module RAS-PROTOCOL-TUNNEL (H.323:06/2006)
-- See also ITU-T H.323 (06/2006)
-- See also the index of all ASN.1 assignments needed in this document

RAS-PROTOCOL-TUNNEL DEFINITIONS AUTOMATIC TAGS ::=
BEGIN

IMPORTS TunnelledProtocol, NonStandardParameter
          FROM H323-MESSAGES;

RasTunnelledSignallingMessage ::= SEQUENCE {
  tunnelledProtocolID  TunnelledProtocol, -- tunnelled signalling protocol ID
  messageContent       SEQUENCE OF OCTET STRING, -- sequence of entire message(s)
  tunnellingRequired   NULL OPTIONAL,
  nonStandardData      NonStandardParameter OPTIONAL,
  ...
}

END

-- Generated by Asnp, the ASN.1 pretty-printer of France Telecom R&D

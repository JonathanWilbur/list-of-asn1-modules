M1 (X.683:07/2002)


-- Module M1 (X.683:07/2002)
-- See also ITU-T X.683 (07/2002)
-- See also the index of all ASN.1 assignments needed in this document

M1 DEFINITIONS AUTOMATIC TAGS ::=
BEGIN

EXPORTS T1;

T1 ::= SET {f1  INTEGER,
            f2  BOOLEAN
}

END

-- Generated by Asnp, the ASN.1 pretty-printer of France Telecom R&D

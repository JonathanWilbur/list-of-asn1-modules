TC-Notation-Extensions (Rec. Q.775:06/1997)


-- Module TC-Notation-Extensions (Q.775:06/1997)-- See also ITU-T Q.775 (06/1997)-- See also the index of all ASN.1 assignments needed in this Recommendation

TC-Notation-Extensions {itu-t recommendation q 775 modules(2)
  notation-extension(4) version1(1)} DEFINITIONS ::=
BEGIN

IMPORTS
  TCMessage{}
    FROM TCAPMessages {itu-t recommendation q 773 modules(2) messages(1)
      version3(3)}
  Bind{}, Unbind{}
    FROM Remote-Operations-Generic-ROS-PDUs {joint-iso-itu-t
      remote-operations(4) generic-ROS-PDUs(6) version1(0)}
  AllOperations{}, ConsumerPerforms{}, SupplierPerforms{}, combine{}
    FROM Remote-Operations-Useful-Definitions {joint-iso-itu-t
      remote-operations(4) useful-definitions(7) version1(0)}
  CONTRACT, OPERATION-PACKAGE
    FROM Remote-Operations-Information-Objects {joint-iso-itu-t
      remote-operations(4) informationObjects(5) version1(0)}
  UniDialoguePDU, uniDialogue-as-id
    FROM UnidialoguePDUs {itu-t recommendation q 773 modules(2)
      unidialoguePDUs(3) version1(1)}
  DialoguePDU, dialogue-as-id
    FROM DialoguePDUs {itu-t recommendation q 773 modules(2) dialoguePDUs(2)
      version1(1)};

APPLICATION-CONTEXT ::= CLASS {
  &amp;associationContract           CONTRACT,
  &amp;dialogueMode                  DialogueMode,
  &amp;termination                   Termination OPTIONAL,
  &amp;componentGrouping             BOOLEAN DEFAULT TRUE,
  &amp;dialogueAndComponentGrouping  BOOLEAN DEFAULT TRUE,
  &amp;AdditionalASEs                OBJECT IDENTIFIER OPTIONAL,
  &amp;AbstractSyntaxes              ABSTRACT-SYNTAX,
  &amp;applicationContextName        OBJECT IDENTIFIER UNIQUE
}
WITH SYNTAX {
  CONTRACT &amp;associationContract
  DIALOGUE MODE &amp;dialogueMode
  [TERMINATION &amp;termination]
  [COMPONENT GROUPING ALLOWED &amp;componentGrouping]
  [DIALOGUE WITH COMPONENTS ALLOWED &amp;dialogueAndComponentGrouping]
  [ADDITIONAL ASES &amp;AdditionalASEs]
  ABSTRACT SYNTAXES &amp;AbstractSyntaxes
  APPLICATION CONTEXT NAME &amp;applicationContextName
}

DialogueMode ::= ENUMERATED {structured(1), unstructured(2)}

Termination ::= ENUMERATED {basic(1), prearranged(2)}

dialogue-abstract-syntax ABSTRACT-SYNTAX ::= {
  DialoguePDU
  IDENTIFIED BY  dialogue-as-id
}

uniDialogue-abstract-syntax ABSTRACT-SYNTAX ::= {
  UniDialoguePDU
  IDENTIFIED BY  uniDialogue-as-id
}

TCSingleAS{OPERATION-PACKAGE:package} ::=
  TCMessage{{AllOperations  {package}}, {AllOperations  {package}}}

TCConsumerAS{OPERATION-PACKAGE:package} ::=
  TCMessage{{ConsumerPerforms  {package}}, {ConsumerPerforms  {package}}}

TCSupplierAS{OPERATION-PACKAGE:package} ::=
  TCMessage{{SupplierPerforms  {package}}, {SupplierPerforms  {package}}}

AllPackagesAS{APPLICATION-CONTEXT:ac} ::=
  TCSingleAS
    {combine{{ac.&amp;associationContract.&amp;OperationsOf |
            ac.&amp;associationContract.&amp;InitiatorConsumerOf |
            ac.&amp;associationContract.&amp;InitiatorSupplierOf},
            {...}, --Illegaly empty, needs to be changed 
            { -- Information Object of class OPERATION-PACKAGE to be defined --}}}

ConnectionAS{APPLICATION-CONTEXT:ac} ::= CHOICE {
  bind    Bind{ac.&amp;associationContract.&amp;connection.&amp;bind},
  unbind  Unbind{ac.&amp;associationContract.&amp;connection.&amp;unbind}
}

END

-- Generated by Asnp, the ASN.1 pretty-printer of France Telecom R&amp;D

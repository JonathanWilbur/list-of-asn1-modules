IN-CS-1-Errors (Q.1218:10/1995)


-- Module IN-CS-1-Errors (Q.1218:10/1995)
-- See also ITU-T Q.1218 (10/1995)
-- See also the index of all ASN.1 assignments needed in this document

IN-CS-1-Errors {itu-t recommendation q 1218 modules(0) cs-1-errors(1)
  version1(0)}
--  This module contains the type definitions for the IN CS-1 errors.
--  Where a parameter of type CHOICE is tagged with a specific tag value, the tag is automatically 
--  replaced with an EXPLICIT tag of the same value.
DEFINITIONS IMPLICIT TAGS ::=
BEGIN

IMPORTS
  ERROR
    FROM Remote-Operations-Information-Objects {joint-iso-itu-t
      remote-operations(4) informationObjects(5) version1(0)}
  InvokeID, UnavailableNetworkResource
    FROM IN-CS-1-Datatypes {itu-t recommendation q 1218 modules(0)
      cs-1-datatypes(2) version1(0)}
  -- err codes
  err-cancelled, err-cancelFailed, err-eTCFailed, err-improperCallerResponse,
    err-missingCustomerRecord, err-missingParameter, err-parameterOutOfRange,
    err-requestedInfoError, err-systemFailure, err-taskRefused,
    err-unavailableResource, err-unexpectedComponentSequence,
    err-unexpectedDataValue, err-unexpectedParameter, err-unknownLegID,
    err-unknownResource
    FROM IN-CS-1-Codes {itu-t recommendation q 1218 modules(0) cs-1-codes(3)
      version1(0)};

--  TYPE DEFINITION FOR  IN CS-1  ERRORS FOLLOWS
cancelled ERROR ::= {CODE  err-cancelled
}

--  The operation has been cancelled.
cancelFailed ERROR ::= {
  PARAMETER
    SEQUENCE {problem
                [0]  ENUMERATED {unknownOperation(0), tooLate(1),
                                 operationNotCancellable(2)},
              operation  [1]  InvokeID}
  CODE       err-cancelFailed
}

--  The operation failed to be cancelled.
eTCFailed ERROR ::= {CODE  err-eTCFailed
}

--  The establish temporary connection failed.
improperCallerResponse ERROR ::= {CODE  err-improperCallerResponse
}

--  The caller response was not as expected.
missingCustomerRecord ERROR ::= {CODE  err-missingCustomerRecord
}

--  The Service Logic Program could not be found in the SCF.
missingParameter ERROR ::= {CODE  err-missingParameter
}

--  An expected optional parameter was not received.
parameterOutOfRange ERROR ::= {CODE  err-parameterOutOfRange
}

--  The parameter was not as expected (e.g. missing or out of range).
requestedInfoError ERROR ::= {
  PARAMETER
    ENUMERATED {unknownRequestedInfo(1), requestedInfoNotAvailable(2)
                                         --  other values FFS
                                         }
  CODE       err-requestedInfoError
}

--  The requested information cannot be found.
systemFailure ERROR ::= {
  PARAMETER  UnavailableNetworkResource
  CODE       err-systemFailure
}

--  The operation could not be completed due to a system failure at the serving physical entity.
taskRefused ERROR ::= {
  PARAMETER
    ENUMERATED {generic(0), unobtainable(1), congestion(2)
                                             --  other values FFS
                                             }
  CODE       err-taskRefused
}

--  An entity normally capable of the task requested cannot or chooses not to perform the task at this 
--  time. This includes error situations like congestion and unobtainable address as used in (e.g. the 
--  connect operation).
unavailableResource ERROR ::= {CODE  err-unavailableResource
}

-- A requested resource is not available at the serving entity.
unexpectedComponentSequence ERROR ::= {CODE  err-unexpectedComponentSequence
}

--  An incorrect sequence of Components was received (e.g."DisconnectForwardConnection" 
--  followed by "PlayAnnouncement").
unexpectedDataValue ERROR ::= {CODE  err-unexpectedDataValue
}

-- The data value was not as expected (e.g. routing number expected but billing number received).
unexpectedParameter ERROR ::= {CODE  err-unexpectedParameter
}

-- A parameter received was not expected.
unknownLegID ERROR ::= {CODE  err-unknownLegID
}

--  Leg not known to the SSF.
unknownResource ERROR ::= {CODE  err-unknownResource
}

-- Resource whose status is being requested is not known to the serving entity.
END

-- Generated by Asnp, the ASN.1 pretty-printer of France Telecom R&D

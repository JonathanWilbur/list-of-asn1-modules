Remote-Operations-Information-Objects (Rec. X.880:07/1994)


-- Module Remote-Operations-Information-Objects (X.880:07/1994)-- See also ITU-T X.880 (1994) Technical Cor. 1 (07/1995)-- See also the index of all ASN.1 assignments needed in this Recommendation

Remote-Operations-Information-Objects {joint-iso-itu-t remote-operations(4)
  informationObjects(5) version1(0)} DEFINITIONS ::=
BEGIN

-- exports everything
IMPORTS
  emptyBind, emptyUnbind
    FROM Remote-Operations-Useful-Definitions {joint-iso-itu-t
      remote-operations(4) useful-definitions(7) version1(0)};

OPERATION ::= CLASS {
  &amp;ArgumentType          OPTIONAL,
  &amp;argumentTypeOptional  BOOLEAN OPTIONAL,
  &amp;returnResult          BOOLEAN DEFAULT TRUE,
  &amp;ResultType            OPTIONAL,
  &amp;resultTypeOptional    BOOLEAN OPTIONAL,
  &amp;Errors                ERROR OPTIONAL,
  &amp;Linked                OPERATION OPTIONAL,
  &amp;synchronous           BOOLEAN DEFAULT FALSE,
  &amp;alwaysReturns         BOOLEAN DEFAULT TRUE,
  &amp;InvokePriority        Priority OPTIONAL,
  &amp;ResultPriority        Priority OPTIONAL,
  &amp;operationCode         Code UNIQUE OPTIONAL
}
WITH SYNTAX {
  [ARGUMENT &amp;ArgumentType
   [OPTIONAL &amp;argumentTypeOptional]]
  [RESULT &amp;ResultType
   [OPTIONAL &amp;resultTypeOptional]]
  [RETURN RESULT &amp;returnResult]
  [ERRORS &amp;Errors]
  [LINKED &amp;Linked]
  [SYNCHRONOUS &amp;synchronous]
  [ALWAYS RESPONDS &amp;alwaysReturns]
  [INVOKE PRIORITY &amp;InvokePriority]
  [RESULT-PRIORITY &amp;ResultPriority]
  [CODE &amp;operationCode]
}

ERROR ::= CLASS {
  &amp;ParameterType          OPTIONAL,
  &amp;parameterTypeOptional  BOOLEAN OPTIONAL,
  &amp;ErrorPriority          Priority OPTIONAL,
  &amp;errorCode              Code UNIQUE OPTIONAL
}
WITH SYNTAX {
  [PARAMETER &amp;ParameterType
   [OPTIONAL &amp;parameterTypeOptional]]
  [PRIORITY &amp;ErrorPriority]
  [CODE &amp;errorCode]
}

OPERATION-PACKAGE ::= CLASS {
  &amp;Both      OPERATION OPTIONAL,
  &amp;Consumer  OPERATION OPTIONAL,
  &amp;Supplier  OPERATION OPTIONAL,
  &amp;id        OBJECT IDENTIFIER UNIQUE OPTIONAL
}
-- continued on the next page
WITH SYNTAX {
  [OPERATIONS &amp;Both]
  [CONSUMER INVOKES &amp;Supplier]
  [SUPPLIER INVOKES &amp;Consumer]
  [ID &amp;id]
}

CONNECTION-PACKAGE ::= CLASS {
  &amp;bind                OPERATION DEFAULT emptyBind,
  &amp;unbind              OPERATION DEFAULT emptyUnbind,
  &amp;responderCanUnbind  BOOLEAN DEFAULT FALSE,
  &amp;unbindCanFail       BOOLEAN DEFAULT FALSE,
  &amp;id                  OBJECT IDENTIFIER UNIQUE OPTIONAL
}
WITH SYNTAX {
  [BIND &amp;bind]
  [UNBIND &amp;unbind]
  [RESPONDER UNBIND &amp;responderCanUnbind]
  [FAILURE TO UNBIND &amp;unbindCanFail]
  [ID &amp;id]
}

CONTRACT ::= CLASS {
  &amp;connection           CONNECTION-PACKAGE OPTIONAL,
  &amp;OperationsOf         OPERATION-PACKAGE OPTIONAL,
  &amp;InitiatorConsumerOf  OPERATION-PACKAGE OPTIONAL,
  &amp;InitiatorSupplierOf  OPERATION-PACKAGE OPTIONAL,
  &amp;id                   OBJECT IDENTIFIER UNIQUE OPTIONAL
}
WITH SYNTAX {
  [CONNECTION &amp;connection]
  [OPERATIONS OF &amp;OperationsOf]
  [INITIATOR CONSUMER OF &amp;InitiatorConsumerOf]
  [RESPONDER CONSUMER OF &amp;InitiatorSupplierOf]
  [ID &amp;id]
}

ROS-OBJECT-CLASS ::= CLASS {
  &amp;Is                    ROS-OBJECT-CLASS OPTIONAL,
  &amp;Initiates             CONTRACT OPTIONAL,
  &amp;Responds              CONTRACT OPTIONAL,
  &amp;InitiatesAndResponds  CONTRACT OPTIONAL,
  &amp;id                    OBJECT IDENTIFIER UNIQUE
}
WITH SYNTAX {
  [IS &amp;Is]
  [BOTH &amp;InitiatesAndResponds]
  [INITIATES &amp;Initiates]
  [RESPONDS &amp;Responds]
  ID &amp;id
}

Code ::= CHOICE {local   INTEGER,
                 global  OBJECT IDENTIFIER
}

Priority ::= INTEGER(0..MAX)

END -- end of Information Object specifications

-- Generated by Asnp, the ASN.1 pretty-printer of France Telecom R&amp;D

XYZ (X.694:01/2004)


-- Module XYZ (X.694:01/2004)
-- See also ITU-T X.694 (01/2004)
-- See also the index of all ASN.1 assignments needed in this document

XYZ -- The module reference is not standardized
DEFINITIONS AUTOMATIC TAGS ::=
BEGIN

Xyz ::= [NAME AS UNCAPITALIZED] XSD.String

Xyz-type ::= SEQUENCE {xyz-attr   [ATTRIBUTE] BOOLEAN OPTIONAL
}

ENCODING-CONTROL XER
	GLOBAL-DEFAULTS MODIFIED-ENCODINGS
	GLOBAL-DEFAULTS CONTROL-NAMESPACE
		"http://www.w3.org/2001/XMLSchema-instance"
END

-- Generated by Asnp, the ASN.1 pretty-printer of France Telecom R&D

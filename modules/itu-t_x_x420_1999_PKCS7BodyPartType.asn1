PKCS7BodyPartType (X.420:06/1999)


-- Module PKCS7BodyPartType (X.420:06/1999)
-- See also ITU-T X.420 (06/1999)
-- See also the index of all ASN.1 assignments needed in this document

PKCS7BodyPartType {joint-iso-itu-t mhs(6) ipms(1) modules(0)
  pkcs7-body-part-type(16)} DEFINITIONS IMPLICIT TAGS ::=
BEGIN

IMPORTS
  -- PKCS#7
  ContentInfo
    FROM PKCS7 {iso(1) member-body(2) usa(840) rsadsi(113549) pkcs(1) 
      7 module(0)}
  -- module not formally defined in the PKCS#7document, therefore defined in Annex O
  -- IPMS Information Objects
  EXTENDED-BODY-PART-TYPE
    FROM IPMSInformationObjects {joint-iso-itu-t mhs(6) ipms(1) modules(0)
      information-objects(2) version-1999(1)}
  -- IPMS Object Identifiers
  id-et-pkcs7
    --==
    FROM IPMSObjectIdentifiers {joint-iso-itu-t mhs(6) ipms(1) modules(0)
      object-identifiers(0) version-1999(1)};

-- PKCS7 body part
pkcs7-body-part EXTENDED-BODY-PART-TYPE ::= {
  DATA  {ContentInfo
         IDENTIFIED BY  id-et-pkcs7}
}

END -- of PKCS7BodyPartType

-- Generated by Asnp, the ASN.1 pretty-printer of France Telecom R&D

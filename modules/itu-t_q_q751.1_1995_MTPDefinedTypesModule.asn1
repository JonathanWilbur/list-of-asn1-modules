MTPDefinedTypesModule (Q.751.1:10/1995)


-- Module MTPDefinedTypesModule (Q.751.1:10/1995)
-- See also ITU-T Q.751.1 (10/1995)
-- See also the index of all ASN.1 assignments needed in this document

MTPDefinedTypesModule {itu-t(0) recommendation q(17) omap(751) mtp(1)
  informationModel(0) asn1Modules(2) mtpDefinedTypesModule(0)} DEFINITIONS
IMPLICIT TAGS ::=
BEGIN

--EXPORTS EVERYTHING
IMPORTS
  AdministrativeState, SimpleNameType, ProbableCause, SpecificProblems,
    PerceivedSeverity, NotificationIdentifier, CorrelatedNotifications,
    AdditionalText, AdditionalInformation
    FROM Attribute-ASN1Module {joint-iso-itu-t ms(9) smi(3) part2(2)
      asn1Module(2) 1}
  NameType, Pointer, ObjectList, PointerOrNull
    FROM ASN1DefinedTypesModule {itu-t recommendation m gnm(3100)
      informationModel(0) asn1Modules(2) asn1DefinedTypesModule(0)}
  ObjectInstance
    FROM CMIP-1 {joint-iso-itu-t ms(9) cmip(1) modules(0) protocol(3)};

mtpInformationModel OBJECT IDENTIFIER ::=
  {itu-t recommendation q(17) omap(751) mtp(1) informationModel(0)}

mtpObjectClass OBJECT IDENTIFIER ::=
  {mtpInformationModel managedObjectClass(3)}

mtpPackage OBJECT IDENTIFIER ::= {mtpInformationModel package(4)}

mtpParameter OBJECT IDENTIFIER ::= {mtpInformationModel parameter(5)}

mtpAttribute OBJECT IDENTIFIER ::= {mtpInformationModel attribute(7)}

mtpNameBinding OBJECT IDENTIFIER ::= {mtpInformationModel nameBinding(6)}

mtpAction OBJECT IDENTIFIER ::= {mtpInformationModel action(9)}

mtpNotification OBJECT IDENTIFIER ::= {mtpInformationModel notification(10)}

mtpSpecificExtensions OBJECT IDENTIFIER ::=
  {mtpInformationModel specificExtensions(0)}

AdditionalName ::=
  IA5String -- the size of this string is implementation dependent

administrativeStateLocked AdministrativeState ::= locked

AlternativeSlCodeList ::= SEQUENCE SIZE (0..15) OF SlCode

CapacityLink ::= INTEGER(0..maxOctetsPerSecondLink)

CapacityLS ::= INTEGER(0..maxOctetsPerSecondLS)

ChangeInLsToAdjSpInfo ::= SEQUENCE {
  oldSignLinkSetTp  NameType,
  newSignLinkSetTp  NameType
}

Cic ::= INTEGER(0..4095)

CongestedState ::= ENUMERATED {notCongested(0), congested(1)}

CongestionControlMethod ::= ENUMERATED {
  unknown(0), ccmQ704International(1), ccmQ704NationalWithPrio(2),
  ccmQ704NationalNoPrioBufferMechanism(3),
  ccmQ704NationalNoPrioTimerMechanism(4)}

CongestionCounting ::= ENUMERATED {octet(0), message(1)}

CongestionLevel ::= ENUMERATED {
  none(0), congestionLevel1(1), congestionLevel2(2), congestionLevel3(3)
}

CongestionReportingBaseObject ::= ENUMERATED {
  routeSet(0), linkSetOfCongestedRouteSet(1), linkOfCongestedRouteSet(2),
  congestedLinkOfCongestedRoute(3)}

CurrentRouteIndicatorList ::= SEQUENCE OF CurrentRouteIndicator

CurrentRouteIndicator ::= INTEGER {
  unknown(0), currentRoute(1), possibleRouteNoFurtherAnalysisPerformed(2),
  possibleRouteSignRouteSetLocked(3), possibleRouteLinkSetUnavailable(4),
  possibleRouteTfpReceived(5), possibleRouteHigherPriorityRouteAvailable(6)
}(0..255)

DpcComponent ::= CHOICE {
  dpc       [0]  PointCode,
  dpcRange  [1]  SEQUENCE {firstDPC  PointCode,
                           lastDPC   PointCode}
}

ErrorCorrectionMethod ::= ENUMERATED {basicRetr(0), prevCyclRetr(1)}

EventsCongestionLevel ::= SEQUENCE {
  events     INTEGER,
  conglevel  CongestionLevel
}

EventsUP ::= SEQUENCE {events    INTEGER,
                       userpart  UserPart
}

FixedPriority ::= Priority

FlexiblePriority ::= Priority

InaccessibleSpInfo ::= SEQUENCE {
  networkIndicator  NetworkIndicator,
  pointCode         PointCode
}

InClsLoadsharingAlgorithm ::= SET OF SlsLinkPriorityList

InfoRequest ::= BIT STRING {
  pointCode(0), pointCodeList(1), routePriorityList(2),
  currentRouteIndicatorList(3)}

InitialLevelIfCongested ::=
  INTEGER(1..3) -- This equals the value s from B.1.2.9.2
         

InLsLoadShareAlgorithm ::= OBJECT IDENTIFIER

L2TimerT1 ::= INTEGER(13000..600000)

-- time, in milliseconds
L2TimerT2 ::= INTEGER(5000..150000)

-- time, in milliseconds
L2TimerT3 ::= INTEGER(1000..14000)

-- time, in milliseconds
L2TimerT4E ::= INTEGER(400..8000)

-- time, in milliseconds
L2TimerT4N ::= INTEGER(7500..120000)

-- time, in milliseconds
L2TimerT5 ::= INTEGER(80..120)

-- time, in milliseconds
L2TimerT6 ::= INTEGER(3000..12000)

-- time, in milliseconds
L2TimerT7 ::= INTEGER(500..6000)

-- time, in milliseconds
LinkSetPriorityListSntx ::= SEQUENCE OF NameType

LinkTPStatus ::= BIT STRING {
  localBlocked(0), remoteBlocked(1), localInhibited(2), remoteInhibited(3),
  failed(4), deactivated(5)}

LoadsharingInformationRouteNePart ::=
  IA5String -- the size of this string is implementation dependent

LoadsharingInformationRouteSetNePart ::=
  IA5String -- the size of this string is implementation dependent

LocalUpUnavailable ::= UserPart

LoopDelay ::= INTEGER

-- time, in milliseconds
--ManagementExtension ::= SEQUENCE {
--	identifier	OBJECT IDENTIFIER,
--	significance	[1]	BOOLEAN DEFAULT FALSE,
--	information	[2]	ANY DEFINED BY identifier }
ManagementExtension ::= SEQUENCE {
  identifier    TYPE-IDENTIFIER.&id({ManagementExtensions}),
  significance  [1]  BOOLEAN DEFAULT FALSE,
  information
    [2]  TYPE-IDENTIFIER.&Type({ManagementExtensions}{@identifier})
}

ManagementExtensions TYPE-IDENTIFIER ::=
  {... -- dynamically extensible information object set --}

maxLinksInLs INTEGER ::= 16

MaxMSUsRetransN1 ::= INTEGER(0..127)

-- lower range is implementation dependent
MaxMSUsRetransN2 ::= INTEGER

maxNoOfScreenedDpcs INTEGER ::= 128

-- This value is suggested by clause 8/Q.705. It is likely that this value is too low for international networks
maxNoOfScreenedOpcs INTEGER ::=
  128

-- This value is suggested by clause 8/Q.705. It is likely that this value is too low for international networks
MaxNumOfTests ::= INTEGER

maxOctetsPerSecondLink INTEGER ::= 8000

maxOctetsPerSecondLS INTEGER ::= 128000

MaxOctRetransN2 ::= INTEGER

MRVTActionResult ::= CHOICE {
  resultOfMRTVT       [0]  ResultOfMRVT,
  reasonForRejection  [1]  ReasonForRejection
}

MRVTFailureString ::= BIT STRING {
  detectedLoop(0), excessiveLengthRoute(1), unknownDestination(2),
  routeInaccessible(3), processingFailure(4), unknownInitiatingSP(5),
  timerExpired(6), spNotAnSTP(7), indirectRoute(8),
  maxNrMRVTestsAlready(9), -- Info from adjacent SP
  unknownParameter(10)}(SIZE (32))

MtpRestarting ::= PointCode

MtpRouteVerifTestResultSntx ::= SEQUENCE {
  testedDestination          PointCode, -- 2.2.2.3 b)/Q.753
  routeTestResult            ResultOfMRVT, -- 2.2.2.3 c)/Q.753
  failureType                [1]  MRVTFailureString OPTIONAL, -- 2.1.1.3.1/Q.754
  routeTrace                 [2]  RouteTrace OPTIONAL, -- 2.2.2.3 d)/Q.753
  pointCodeInfo              [3]  PointCode OPTIONAL,
  pointCodeListInfo          [4]  PointCodeList OPTIONAL,
  routePriorityListInfo      [5]  RoutePriorityListInfo OPTIONAL,
  copyData                   [6]  OCTET STRING OPTIONAL, -- 2.2.2.3 e)/Q.753
  currentRouteIndicatorList  [7]  CurrentRouteIndicatorList OPTIONAL
}

NetworkIndicator ::= ENUMERATED {
  internationalNetwork1(0), internationalNetwork2(1), nationalNetwork1(2),
  nationalNetwork2(3)}

NumCongStates ::= INTEGER(0..3)

NumberOfNormallyActiveSignLinksTps ::= INTEGER(0..16)

NumberOfThresholdLevels ::= INTEGER(2 | 3)

PeriodicLinkTestFlag ::= ENUMERATED {on(0), off(1)}

periodicTestFlagDefault PeriodicLinkTestFlag ::= off

PointCode ::= INTEGER

PointCodeList ::= SEQUENCE OF PointCode

PointerList ::= SET OF Pointer

Priority ::= INTEGER

-- maximum value is implementation dependent
PriorityInfo ::= INTEGER {
  unknown(0), firstChoice(1), secondChoice(2), thirdChoice(3)}(0..255)

PriorityMode ::= ENUMERATED {
  insert(0), equal(1), exchangeSingle(2), exchangeGroup(3)}

priorityModeDefault PriorityMode ::= insert

localUserPartUnavailable ProbableCause ::=
  globalValue:{mtpSpecificExtensions 1}

q752Item1p02 ProbableCause ::= globalValue:{mtpSpecificExtensions 102}

q752Item1p10 ProbableCause ::= globalValue:{mtpSpecificExtensions 110}

q752Item2p10 ProbableCause ::= globalValue:{mtpSpecificExtensions 210}

q752Item2p16 ProbableCause ::= globalValue:{mtpSpecificExtensions 216}

q752Item2p18 ProbableCause ::= globalValue:{mtpSpecificExtensions 218}

q752Item3p06 ProbableCause ::= globalValue:{mtpSpecificExtensions 306}

q752Item3p11 ProbableCause ::= globalValue:{mtpSpecificExtensions 311}

q752Item4p03 ProbableCause ::= globalValue:{mtpSpecificExtensions 403}

q752Item4p05 ProbableCause ::= globalValue:{mtpSpecificExtensions 405}

q752Item4p11 ProbableCause ::= globalValue:{mtpSpecificExtensions 411}

q752Item4p13 ProbableCause ::= globalValue:{mtpSpecificExtensions 413}

q752Item5p01 ProbableCause ::= globalValue:{mtpSpecificExtensions 501}

q752Item5p05 ProbableCause ::= globalValue:{mtpSpecificExtensions 505}

q752Item5p06 ProbableCause ::= globalValue:{mtpSpecificExtensions 506}

q752Item5p07 ProbableCause ::= globalValue:{mtpSpecificExtensions 507}

q752Item5p08 ProbableCause ::= globalValue:{mtpSpecificExtensions 508}

remoteUserPartUnavailable ProbableCause ::=
  globalValue:{mtpSpecificExtensions 2}

abnormalFIBRorBSNR SpecificProblems ::= {oi:{mtpSpecificExtensions 3}}

excessiveAckDelay SpecificProblems ::= {oi:{mtpSpecificExtensions 4}}

excessiveCongDuration SpecificProblems ::= {oi:{mtpSpecificExtensions 6}}

excessiveErrorRate SpecificProblems ::= {oi:{mtpSpecificExtensions 5}}

remoteUPInaccessible SpecificProblems ::= {oi:{mtpSpecificExtensions 9}}

remoteUPUnequipped SpecificProblems ::= {oi:{mtpSpecificExtensions 8}}

remoteUPUnknown SpecificProblems ::= {oi:{mtpSpecificExtensions 7}}

ReasonForRejection ::= ENUMERATED {
  routeTestInstanceLocked(10), routeTestInstanceDisabled(11),
  routeTestInstanceBusy(12), routeTestAlreadyInProgress(13)}

ReceiveCongestionThresholdAbatement ::= INTEGER

ReceiveCongestionThresholdOnset ::= INTEGER

RelatedLinkGroupNumber ::= INTEGER(0..15)

RemoteExchangeLabel ::= IA5String

-- the size of this string is implementation dependent
RemoteUpUnavailable ::= SEQUENCE {
  pointCode  [0]  PointCode,
  userPart   [1]  UserPart
}

ResultMtpRouteTest ::= SEQUENCE {
  testedDestination      PointCode,
  routeTestActionResult  MRVTActionResult,
  failureType            [1]  MRVTFailureString OPTIONAL,
  ...
}

ResultOfAction ::= ENUMERATED {
  success(0), unsuccessful(1), notPerformed(2), linkAlreadyInhibited(3),
  linkNotInhibited(4), wrongClassReferenced(5), signTermNonExisting(6),
  signTermAlreadyReferenced(7), wrongSignLinkTPStatus(8), ...
  }

ResultOfMRVT ::= ENUMERATED {
  success(0), partialSuccess(1), -- 2.1.1.3.2/Q.754, Partial Success
  failure(2) -- 2.1.1.3.1/Q.754, Failure--}

ReturnUnknownParams ::= BIT STRING {tag15(0), tag16(1), tag17(2)}(SIZE (32))

RoutePriorityListInfo ::= SEQUENCE OF PriorityInfo

RouteSetUnavailable ::= OBJECT IDENTIFIER

RouteTrace ::= CHOICE {
  success               [0] IMPLICIT PointCodeList,
  detectedLoop          [1] IMPLICIT PointCodeList,
  excessiveLengthRoute  [2] IMPLICIT PointCodeList,
  unknownDestination    [3] IMPLICIT NULL,
  routeInaccessible     [4] IMPLICIT PointCodeList,
  processingFailure     [5] IMPLICIT NULL,
  unknownInitiatingSP   [6] IMPLICIT PointCode,
  timerExpired          [7] IMPLICIT PointCodeList,
  spNotAnSTP            [8] IMPLICIT PointCodeList
}

ScreenedOpcsOrLinkSetsList ::=
  SET SIZE (0..maxNoOfScreenedOpcs) OF
    SEQUENCE {screenedOpcOrLinkset  StpScreeningTableLineId,
              messageTreatment      TreatmentOf}

ScreeningByLinkSetOrByOpc ::= ENUMERATED {byOpc(0), byIncomingLinkset(1)}

Seconds ::= INTEGER

SignLinkSetTpId ::= NameType

SIOType ::= SEQUENCE {
  service
    ENUMERATED {signallingNetworkManagement(0), signallingNetworkTesting(1),
                sccp(3), tup(4), isup(5), dup(6), mt(8), b-isup(9), siup(10),
                ...
                },
  subService  ENUMERATED {internationalNetwork(0), nationalNetwork(2), ...
                          }
}

SignRouteSetNePartName ::= IA5String

-- the size of this string is implementation dependent
SlCode ::= INTEGER(0..15)

Sls ::= INTEGER(0..15)

SLSCodeCurrentList ::= SlsCodeList

SlsCodeList ::= SET SIZE (0..16) OF Sls

-- Each Sls value can occur at most once in a given SET
SlsCodeNormalList ::=
  SlsCodeList

SlsLinkPriorityList ::= SEQUENCE {
  slsCode                [0]  Sls,
  normalSlcCode          [1]  SlCode,
  alternativeSlCodeList  [2]  AlternativeSlCodeList
}

StmChannel ::= INTEGER(1..31)

SpecificDpc ::= PointCode

SpType ::= ENUMERATED {sep(0), step(1), stp(2)}

SS7OnOccEventInfo ::= SEQUENCE {
  probableCause            ProbableCause,
  specificProblems         [1]  SpecificProblems OPTIONAL,
  perceivedSeverity        PerceivedSeverity,
  notificationIdentifier   [5]  NotificationIdentifier OPTIONAL,
  correlatedNotifications  [6]  CorrelatedNotifications OPTIONAL,
  additionalText           AdditionalText OPTIONAL,
  additionalInformation    [10]  AdditionalInformation OPTIONAL
}

StartMtpRouteTest ::= SEQUENCE {
  testDestination      PointCode,
  traceRequested       BOOLEAN,
  threshold            ThresholdN,
  infoRequest          [0]  InfoRequest OPTIONAL,
  returnUnknownParams  [1]  ReturnUnknownParams OPTIONAL,
  directRouteCheck     [2]  BOOLEAN OPTIONAL
}

StpScreeningElement ::= SEQUENCE {
  designatedDPC     DpcComponent,
  messageTreatment  TreatmentOf
}

StpScreeningTableLineContent ::=
  SET SIZE (1..maxNoOfScreenedDpcs) OF StpScreeningElement

StpScreeningTableLineId ::= CHOICE {
  designatedLinkSet  [0]  SignLinkSetTpId,
  designatedOPC      [1]  PointCode
}

StpScreeningTableListMode ::= BOOLEAN

SuermNSU ::= INTEGER(0..256)

-- lower range is implementation dependent
SuermThresh ::= INTEGER(32 | 64) -- (minSuermThresh or maxSuermThres)
                       

TestResult ::= BIT STRING {
  detectedLoop(0), excessiveLengthRoute(1), unknownDestination(2),
  routeInaccessible(3), processingFailure(4), unknownInitiatingSP(5),
  timerExpired(6), spNotAnSTP(7), indirectRoute(8), maxNrMRVTestsAlready(9)
}(SIZE (32))

ThresholdN ::= INTEGER

TimeD ::= INTEGER

TimerValue ::= INTEGER(0..360000)

TransmissionCongestionThresholdAbatementLevel1 ::= INTEGER

TransmissionCongestionThresholdAbatementLevel2 ::= INTEGER

TransmissionCongestionThresholdAbatementLevel3 ::= INTEGER

TransmissionCongestionThresholdDiscardLevel1 ::= INTEGER

TransmissionCongestionThresholdDiscardLevel2 ::= INTEGER

TransmissionCongestionThresholdDiscardLevel3 ::= INTEGER

TransmissionCongestionThresholdOnsetLevel1 ::= INTEGER

TransmissionCongestionThresholdOnsetLevel2 ::= INTEGER

TransmissionCongestionThresholdOnsetLevel3 ::= INTEGER

TransmissionRate ::= ENUMERATED {kbits4point8(0), kbits56(1), kbits64(2)}

TreatmentOf ::= ENUMERATED {normal(0), discard(1)}

UserPart ::= ENUMERATED {
  isup(5), sccp(3), tup(4), dup(6), mt(8), b-isup(9), siup(10), ...
  }

END -- end of MTPDefinedTypesModule

-- Generated by Asnp, the ASN.1 pretty-printer of France Telecom R&D

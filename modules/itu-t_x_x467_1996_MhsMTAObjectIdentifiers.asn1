MhsMTAObjectIdentifiers (X.467:10/1996)


-- Module MhsMTAObjectIdentifiers (X.467:10/1996)
-- See also ITU-T X.467 (10/1996)
-- See also the index of all ASN.1 assignments needed in this document

MhsMTAObjectIdentifiers {joint-iso-itu-t mhs(6) management(9) mta(8) 
  modules(8) object-identifiers(0)} DEFINITIONS IMPLICIT TAGS ::=
BEGIN

--	Prologue
--	Exports everything
IMPORTS --  nothing -- ;

ID ::= OBJECT IDENTIFIER

--	MHS management
mhs-management ID ::=
  {joint-iso-itu-t mhs(6) management(9)} --  Not definitive

--	MTA Entity
id-mta ID ::= {mhs-management  8} --  imported from X.462

--	Template types
id-moc ID ::= {id-mta  0} --	Managed Object Class templates

id-package ID ::= {id-mta  1} --	Package templates

id-attribute ID ::= {id-mta  2} --	Attribute templates

id-name-binding ID ::= {id-mta  7} --	Name Binding templates

id-modules ID ::= {id-mta  8} --	Modules 

-- Not definitive
--	Managed Object Classes
id-moc-adjMTA ID ::= {id-moc  0}

id-moc-association ID ::= {id-moc  1}

id-moc-conversionFunction ID ::= {id-moc  2}

id-moc-distributionListFunction ID ::= {id-moc  3}

id-moc-mpr ID ::= {id-moc  4}

id-moc-mprList ID ::= {id-moc  5}

id-moc-mta ID ::= {id-moc  6}

id-moc-mtsUser ID ::= {id-moc  7}

id-moc-perfFunctionCurrentData ID ::= {id-moc  8}

id-moc-perfFunctionHistoryData ID ::= {id-moc  9}

id-moc-perfMTACurrentData ID ::= {id-moc  10}

id-moc-perfMTAHistoryData ID ::= {id-moc  11}

id-moc-routingFunction ID ::= {id-moc  12}

id-moc-secAdjMTA ID ::= {id-moc  13}

id-moc-secAssociation ID ::= {id-moc  14}

id-moc-secConversion ID ::= {id-moc  15}

id-moc-secGenROACFunction ID ::= {id-moc  16}

id-moc-secMessage ID ::= {id-moc  17}

id-moc-secMtsUser ID ::= {id-moc  18}

id-moc-secProbe ID ::= {id-moc  19}

id-moc-secReport ID ::= {id-moc  20}

id-moc-SecVerifGenMsgFunction ID ::= {id-moc  21}

id-moc-SecVerifGenRecipFunction ID ::= {id-moc  22}

id-moc-SecVerifMOACFunction ID ::= {id-moc  23}

id-moc-SecVerifPOACFunction ID ::= {id-moc  24}

id-moc-SecVerifROACFunction ID ::= {id-moc  25}

--	Packages
id-package-adjMTAPackage ID ::= {id-package  0}

id-package-associationPackage ID ::= {id-package  1}

id-package-conversionPackage ID ::= {id-package  2}

id-package-defaultDeliveryControlsPackage ID ::= {id-package  3}

id-package-dirServiceReferencePackage ID ::= {id-package  4}

id-package-distributionListPackage ID ::= {id-package  5}

id-package-filterPackage ID ::= {id-package  6}

id-package-mdAssignedAlternateRecipientPackage ID ::= {id-package  7}

id-package-mprListPackage ID ::= {id-package  8}

id-package-mprPackage ID ::= {id-package  9}

id-package-mprProcessingControlPackage ID ::= {id-package  10}

id-package-mtaFunctionStatisticsPackage ID ::= {id-package  11}

id-package-mtaPackage ID ::= {id-package  12}

id-package-mtaStatisticsPackage ID ::= {id-package  13}

id-package-mtsUserPackage ID ::= {id-package  14}

id-package-restrictedDeliveryPackage ID ::= {id-package  15}

id-package-routingPackage ID ::= {id-package  16}

id-package-secAdjMTAPackage ID ::= {id-package  17}

id-package-secAssociationPackage ID ::= {id-package  18}

id-package-secConversionPackage ID ::= {id-package  19}

id-package-secGenROACFunctionPackage ID ::= {id-package  20}

id-package-secMessagePackage ID ::= {id-package  21}

id-package-secMtsUserPackage ID ::= {id-package  22}

id-package-secProbePackage ID ::= {id-package  23}

id-package-secReportPackage ID ::= {id-package  24}

id-package-secureRedirectionPackage ID ::= {id-package  25}

id-package-SecurityAlarmPackage ID ::= {id-package  26}

id-package-secVerifGenMsgFunctionPackage ID ::= {id-package  27}

id-package-secVerifGenRecipFunctionPackage ID ::= {id-package  28}

id-package-secVerifMOACFunctionPackage ID ::= {id-package  29}

id-package-secVerifPOACFunctionPackage ID ::= {id-package  30}

id-package-secVerifROACFunctionPackage ID ::= {id-package  31}

id-package-simpleCredentialsPackage ID ::= {id-package  32}

id-package-simpleRedirectionPackage ID ::= {id-package  33}

id-package-statesOfMtaFunctionPackage ID ::= {id-package  34}

--	Attributes
id-attribute-adjMtaAccessPointAddress ID ::= {id-attribute  0}

id-attribute-adjMtaGlobalDomainId ID ::= {id-attribute  1}

id-attribute-adjMtaMaxMessageSize ID ::= {id-attribute  2}

id-attribute-adjMtaName ID ::= {id-attribute  3}

id-attribute-adjMtaObjectInstanceId ID ::= {id-attribute  4}

id-attribute-adjMtaPossibleConversions ID ::= {id-attribute  5}

id-attribute-adjMtaSimpleCredentials ID ::= {id-attribute  6}

id-attribute-adjMtaStrongCredentials ID ::= {id-attribute  7}

id-attribute-adjMtaSupportedApplicationContexts ID ::= {id-attribute  8}

id-attribute-applicationContext ID ::= {id-attribute  9}

id-attribute-arrivalTime ID ::= {id-attribute  10}

id-attribute-associationInitiator ID ::= {id-attribute  11}

id-attribute-associationObjectInstanceId ID ::= {id-attribute  12}

id-attribute-bilateralDeferral ID ::= {id-attribute  13}

id-attribute-colocated ID ::= {id-attribute  14}

id-attribute-contentIntegrityCheck ID ::= {id-attribute  15}

id-attribute-contentType ID ::= {id-attribute  16}

id-attribute-contentTypesSupported ID ::= {id-attribute  17}

id-attribute-conversionCredentials ID ::= {id-attribute  18}

id-attribute-conversionFunctionObjectInstanceId ID ::= {id-attribute  19}

id-attribute-conversionSecurityContext ID ::= {id-attribute  20}

id-attribute-conversionSecurityLabels ID ::= {id-attribute  21}

id-attribute-conversionType ID ::= {id-attribute  22}

id-attribute-creationTime ID ::= {id-attribute  23}

id-attribute-defaultNonUrgentMprExpiryDuration ID ::= {id-attribute  24}

id-attribute-defaultNormalMprExpiryDuration ID ::= {id-attribute  25}

id-attribute-defaultPermissibleContentTypes ID ::= {id-attribute  26}

id-attribute-defaultPermissibleEITs ID ::= {id-attribute  27}

id-attribute-defaultPermissibleLowestPriority ID ::= {id-attribute  28}

id-attribute-defaultPermissibleMaxContentLength ID ::= {id-attribute  29}

id-attribute-defaultPermissibleOperations ID ::= {id-attribute  30}

id-attribute-defaultUrgentMprExpiryDuration ID ::= {id-attribute  31}

id-attribute-deferralTime ID ::= {id-attribute  32}

id-attribute-directoryName ID ::= {id-attribute  33}

id-attribute-disallowedMessages ID ::= {id-attribute  34}

id-attribute-distributionListObjectInstanceId ID ::= {id-attribute  35}

id-attribute-eits ID ::= {id-attribute  36}

id-attribute-forcedExpiryDuration ID ::= {id-attribute  37}

id-attribute-forcedProcessingPriority ID ::= {id-attribute  38}

id-attribute-globalDomainId ID ::= {id-attribute  39}

id-attribute-heldByManager ID ::= {id-attribute  40}

id-attribute-informationLossSuspected ID ::= {id-attribute  41}

id-attribute-initiatorAccessPointAddress ID ::= {id-attribute  42}

id-attribute-initiatorCredentials ID ::= {id-attribute  43}

id-attribute-initiatorSecurityContext ID ::= {id-attribute  44}

id-attribute-initiatorStrongCredentials ID ::= {id-attribute  45}

id-attribute-lastAdjMtaName ID ::= {id-attribute  46}

id-attribute-localMTAMaxMessageSize ID ::= {id-attribute  47}

id-attribute-localMTASimpleCredentials ID ::= {id-attribute  48}

id-attribute-localMTAStrongCredentials ID ::= {id-attribute  49}

id-attribute-maxAdjMTAInboundAssocs ID ::= {id-attribute  50}

id-attribute-maxAdjMTAOutboundAssocs ID ::= {id-attribute  51}

id-attribute-maxFunctionProcessingTime ID ::= {id-attribute  52}

id-attribute-maxMTAResponseTime ID ::= {id-attribute  53}

id-attribute-maxMtsUserInboundAssocs ID ::= {id-attribute  54}

id-attribute-maxMtsUsersOutboundAssocs ID ::= {id-attribute  55}

id-attribute-maxSizeMprDelivered ID ::= {id-attribute  56}

id-attribute-maxSizeMprPassingFunction ID ::= {id-attribute  57}

id-attribute-maxSizeMprSubmitted ID ::= {id-attribute  58}

id-attribute-maxSizeMprTransferredIn ID ::= {id-attribute  59}

id-attribute-maxSizeMprTransferredOut ID ::= {id-attribute  60}

id-attribute-mdAssignedAlternateRecipient ID ::= {id-attribute  61}

id-attribute-meanFunctionProcessingTime ID ::= {id-attribute  62}

id-attribute-meanMTAResponseTime ID ::= {id-attribute  63}

id-attribute-meanNbOfStoredMpr ID ::= {id-attribute  64}

id-attribute-meanSizeMprDelivered ID ::= {id-attribute  65}

id-attribute-meanSizeMprPassingFunction ID ::= {id-attribute  66}

id-attribute-meanSizeMprSubmitted ID ::= {id-attribute  67}

id-attribute-meanSizeMprTransferredIn ID ::= {id-attribute  68}

id-attribute-meanSizeMprTransferredOut ID ::= {id-attribute  69}

id-attribute-meanStorageOccupied ID ::= {id-attribute  70}

id-attribute-messageContentSize ID ::= {id-attribute  71}

id-attribute-messageEncAlg ID ::= {id-attribute  72}

id-attribute-messageMOACAlg ID ::= {id-attribute  73}

id-attribute-messageOriginatorCertificate ID ::= {id-attribute  74}

id-attribute-messageOriginAuthenticationCheck ID ::= {id-attribute  75}

id-attribute-messageSecurityLabel ID ::= {id-attribute  76}

id-attribute-messageToken ID ::= {id-attribute  77}

id-attribute-minFunctionProcessingTime ID ::= {id-attribute  78}

id-attribute-minMTAResponseTime ID ::= {id-attribute  79}

id-attribute-minSizeMprDelivered ID ::= {id-attribute  80}

id-attribute-minSizeMprPassingFunction ID ::= {id-attribute  81}

id-attribute-minSizeMprSubmitted ID ::= {id-attribute  82}

id-attribute-minSizeMprTransferredIn ID ::= {id-attribute  83}

id-attribute-minSizeMprTransferredOut ID ::= {id-attribute  84}

id-attribute-mprInfo ID ::= {id-attribute  85}

id-attribute-mprListObjectInstanceId ID ::= {id-attribute  86}

id-attribute-mprObjectInstanceId ID ::= {id-attribute  87}

id-attribute-mtaName ID ::= {id-attribute  88}

id-attribute-mtsIdentifier ID ::= {id-attribute  89}

id-attribute-mtsUserAccessPointAddress ID ::= {id-attribute  90}

id-attribute-mtsUserDeliverableContentTypes ID ::= {id-attribute  91}

id-attribute-mtsUserDeliverableEits ID ::= {id-attribute  92}

id-attribute-mtsUserDeliverableMaxContentLength ID ::= {id-attribute  93}

id-attribute-mtsUserDeliveryControls ID ::= {id-attribute  94}

id-attribute-mtsUserName ID ::= {id-attribute  95}

id-attribute-mtsUserObjectInstanceId ID ::= {id-attribute  96}

id-attribute-mtsUserPreferredDeliveryMethod ID ::= {id-attribute  97}

id-attribute-mtsUserSimpleCredentials ID ::= {id-attribute  98}

id-attribute-mtsUserStrongCredentials ID ::= {id-attribute  99}

id-attribute-mtsUserSupportedApplicationContexts ID ::= {id-attribute  100}

id-attribute-mtsUserType ID ::= {id-attribute  101}

id-attribute-newMessageEncAlg ID ::= {id-attribute  102}

id-attribute-newMessageMOACAlg ID ::= {id-attribute  103}

id-attribute-newMessageOriginatorCertificate ID ::= {id-attribute  104}

id-attribute-newRecipientCicAlg ID ::= {id-attribute  105}

id-attribute-newRecipientName ID ::= {id-attribute  106}

id-attribute-newRecipientTokenAlg ID ::= {id-attribute  107}

id-attribute-newRecipientTokenEncAlg ID ::= {id-attribute  108}

id-attribute-newRecipientTokenSigAlg ID ::= {id-attribute  109}

id-attribute-nextAdjMTAName ID ::= {id-attribute  110}

id-attribute-nrOfMprDeferred ID ::= {id-attribute  111}

id-attribute-nrOfMprDelivered ID ::= {id-attribute  112}

id-attribute-nrOfInvocations ID ::= {id-attribute  113}

id-attribute-nrOfRecipientsProcessed ID ::= {id-attribute  114}

id-attribute-nrOfMprRedirected ID ::= {id-attribute  115}

id-attribute-nrOfMprRejected ID ::= {id-attribute  116}

id-attribute-nrOfRejectedInvocations ID ::= {id-attribute  117}

id-attribute-nrOfMprSubmitted ID ::= {id-attribute  118}

id-attribute-nrOfMprTransferredIn ID ::= {id-attribute  119}

id-attribute-nrOfMprTransferredOut ID ::= {id-attribute  120}

id-attribute-originatorName ID ::= {id-attribute  121}

id-attribute-permittedMessages ID ::= {id-attribute  122}

id-attribute-priority ID ::= {id-attribute  123}

id-attribute-priorityList ID ::= {id-attribute  124}

id-attribute-probeOriginatorCertificate ID ::= {id-attribute  125}

id-attribute-probeOriginAuthenticationCheck ID ::= {id-attribute  126}

id-attribute-probePOACAlg ID ::= {id-attribute  127}

id-attribute-probeSecurityLabel ID ::= {id-attribute  128}

id-attribute-processingState ID ::= {id-attribute  129}

id-attribute-processingSummary ID ::= {id-attribute  130}

id-attribute-proofOfDelivery ID ::= {id-attribute  131}

id-attribute-proofOfDeliveryRequest ID ::= {id-attribute  132}

id-attribute-recipientCertificate ID ::= {id-attribute  133}

id-attribute-recipientCicAlg ID ::= {id-attribute  134}

id-attribute-recipientName ID ::= {id-attribute  135}

id-attribute-recipientsNames ID ::= {id-attribute  136}

id-attribute-recipientTokenAlg ID ::= {id-attribute  137}

id-attribute-recipientTokenEncAlg ID ::= {id-attribute  138}

id-attribute-recipientTokenSigAlg ID ::= {id-attribute  139}

id-attribute-redirectionRecipient ID ::= {id-attribute  140}

id-attribute-redirections ID ::= {id-attribute  141}

id-attribute-reportOriginatorCertificate ID ::= {id-attribute  142}

id-attribute-reportOriginAuthenticationCheck ID ::= {id-attribute  143}

id-attribute-reportROACAlg ID ::= {id-attribute  144}

id-attribute-reportSecurityLabel ID ::= {id-attribute  145}

id-attribute-responderAccessPointAddress ID ::= {id-attribute  146}

id-attribute-responderCredentials ID ::= {id-attribute  147}

id-attribute-responderStrongCredentials ID ::= {id-attribute  148}

id-attribute-routingFunctionObjectInstanceId ID ::= {id-attribute  149}

id-attribute-secAdjMTAObjectInstanceId ID ::= {id-attribute  150}

id-attribute-secAssociationObjectInstanceId ID ::= {id-attribute  151}

id-attribute-secConversionObjectInstanceId ID ::= {id-attribute  152}

id-attribute-secGenROACObjectInstanceId ID ::= {id-attribute  153}

id-attribute-secMessageObjectInstanceId ID ::= {id-attribute  154}

id-attribute-secMtsUserObjectInstanceId ID ::= {id-attribute  155}

id-attribute-secProbeObjectInstanceId ID ::= {id-attribute  156}

id-attribute-secReportObjectInstanceId ID ::= {id-attribute  157}

id-attribute-securityLabels ID ::= {id-attribute  158}

id-attribute-secVerifGenMsgObjectInstanceId ID ::= {id-attribute  159}

id-attribute-SecVerifGenRecipObjectInstanceId ID ::= {id-attribute  161}

id-attribute-secVerifPOACObjectInstanceId ID ::= {id-attribute  162}

id-attribute-secVerifROACObjectInstanceId ID ::= {id-attribute  163}

id-attribute-supportedApplicationContexts ID ::= {id-attribute  164}

id-attribute-typeOfMpr ID ::= {id-attribute  165}

id-attribute-waitTimeToRelease ID ::= {id-attribute  166}

--	Name Bindings
id-name-binding-adjMTA-mta ID ::= {id-name-binding  0}

id-name-binding-association-adjMTA ID ::= {id-name-binding  1}

id-name-binding-association-MtsUser ID ::= {id-name-binding  2}

id-name-binding-conversionCurrentData-ConversionFunction ID ::=
  {id-name-binding  3}

id-name-binding-conversionFunction-mta ID ::= {id-name-binding  4}

id-name-binding-conversionHistoryData-ConversionCurrentData ID ::=
  {id-name-binding  5}

id-name-binding-distributionListFunction-mta ID ::= {id-name-binding  6}

id-name-binding-dLCurrentData-distibutionListFunction ID ::=
  {id-name-binding  7}

id-name-binding-dLHistoryData-dLCurrentData ID ::= {id-name-binding  8}

id-name-binding-mpr-mprList ID ::= {id-name-binding  9}

id-name-binding-mprlist-mta ID ::= {id-name-binding  10}

id-name-binding-mta-md ID ::= {id-name-binding  11}

id-name-binding-MtsUser-mta ID ::= {id-name-binding  12}

id-name-binding-perfMTACurrentData-mta ID ::= {id-name-binding  13}

id-name-binding-perfMTAHistoryData-perfMTACurrentData ID ::=
  {id-name-binding  14}

id-name-binding-routing-mta ID ::= {id-name-binding  15}

id-name-binding-routingCurrentData-routingFunction ID ::= {id-name-binding  16}

id-name-binding-routingHistoryData-routingCurrentData ID ::=
  {id-name-binding  17}

id-name-binding-routingIndicator-routing ID ::= {id-name-binding  18}

id-name-binding-secAdjMTA-adjMTA ID ::= {id-name-binding  19}

id-name-binding-secAssociation-association ID ::= {id-name-binding  20}

id-name-binding-secConversion-conversionFunction ID ::= {id-name-binding  21}

id-name-binding-secDistributionList-distributionListFunction ID ::=
  {id-name-binding  22}

id-name-binding-secGenROACFunction-mta ID ::= {id-name-binding  23}

id-name-binding-secMessage-mpr ID ::= {id-name-binding  24}

id-name-binding-secMtsUser-MtsUser ID ::= {id-name-binding  25}

id-name-binding-secProbe-mpr ID ::= {id-name-binding  26}

id-name-binding-secReport-mpr ID ::= {id-name-binding  27}

id-name-binding-secRouting-routingIndicator ID ::= {id-name-binding  28}

id-name-binding-secVerifGenMsgFunction-mta ID ::= {id-name-binding  29}

id-name-binding-secVerifGenRecipFunction-mta ID ::= {id-name-binding  30}

id-name-binding-secVerifMOACFunction-mta ID ::= {id-name-binding  31}

id-name-binding-secVerifPOACFunction-mta ID ::= {id-name-binding  32}

id-name-binding-secVerifROACFunction-mta ID ::= {id-name-binding  33}

id-name-binding-thresholdData-conversionCurrentData ID ::=
  {id-name-binding  34}

id-name-binding-thresholdData-dLCurrentData ID ::= {id-name-binding  35}

id-name-binding-thresholdData-perfMTACurrentData ID ::= {id-name-binding  36}

id-name-binding-thresholdData-routingCurrentData ID ::= {id-name-binding  37}

END --  of MhsMgntMTAObjectIdentifiers

-- Generated by Asnp, the ASN.1 pretty-printer of France Telecom R&D

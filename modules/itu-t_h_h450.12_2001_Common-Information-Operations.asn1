Common-Information-Operations (H.450.12:07/2001)


-- Module Common-Information-Operations (H.450.12:07/2001)
-- See also ITU-T H.450.12 (07/2001)
-- See also the index of all ASN.1 assignments needed in this document

Common-Information-Operations {itu-t recommendation h 450 12 version1(0)
  common-information-operations(0)} DEFINITIONS AUTOMATIC TAGS ::=
BEGIN

IMPORTS
  OPERATION, ERROR
    FROM Remote-Operations-Information-Objects {joint-iso-itu-t
      remote-operations(4) informationObjects(5) version1(0)}
  EXTENSION, Extension{}
    FROM Manufacturer-specific-service-extension-definition {itu-t
      recommendation h 450 1 version1(0) msi-definition(18)}
  MixedExtension, undefined
    FROM Call-Hold-Operations {itu-t recommendation h 450 4 version1(0)
      call-hold-operations(0)};

H323CommonInformationOperations OPERATION ::= {cmnRequest | cmnInform}

cmnRequest OPERATION ::= {
  ARGUMENT  DummyArg
  OPTIONAL  TRUE
  RESULT    CmnArg
  ERRORS    {undefined}
  CODE      local:84
}

cmnInform OPERATION ::= {
  ARGUMENT         CmnArg
  RETURN RESULT    FALSE
  ALWAYS RESPONDS  FALSE
  CODE             local:85
}

CmnArg ::= SEQUENCE {
  featureList     FeatureList OPTIONAL,
  featureValues   FeatureValues OPTIONAL,
  featureControl  FeatureControl OPTIONAL,
  extension       SEQUENCE SIZE (0..255) OF MixedExtension OPTIONAL,
  ...
}

DummyArg ::= SEQUENCE {
  extensionArg  SEQUENCE SIZE (0..255) OF MixedExtension OPTIONAL
}

FeatureList ::= SEQUENCE {
  -- indicates capabilities of the endpoint sending the FeatureList
  ssCFreRoutingSupported         NULL OPTIONAL, -- Call Forwarding rerouting
  
  -- supported meaningful only in
  -- forward direction during call
  -- establishment 
  ssCTreRoutingSupported         NULL OPTIONAL, -- Call Transfer rerouting
  
  -- supported meaningful both in
  -- forward & backward direction
  -- during call establishment 
  ssCCBSPossible                 NULL OPTIONAL, -- CCBS possible meaningful only
  
  -- in backward direction before
  -- receipt of ALERTING/CONNECT 
  ssCCNRPossible                 NULL OPTIONAL, -- CCNR possible meaningful only
  
  -- in backward direction before
  -- receipt of CONNECT 
  ssCOSupported                  NULL OPTIONAL, -- Call Offer supported
  
  -- meaningful only in backward
  -- direction during call
  -- establishment 
  -- Call Intrusion
  ssCIForcedReleaseSupported     NULL OPTIONAL, -- meaningful only in
  
  -- backward direction 
  ssCIIsolationSupported         NULL OPTIONAL, -- meaningful only in
  
  -- backward direction 
  ssCIWaitOnBusySupported        NULL OPTIONAL, -- meaningful only in
  
  -- backward direction 
  ssCISilentMonitoringSupported  NULL OPTIONAL, -- meaningful only in
  
  -- backward direction 
  ssCIConferenceSupported        NULL OPTIONAL, -- meaningful only in
  
  -- backward direction 
  -- Call Hold
  ssCHFarHoldSupported           NULL OPTIONAL, -- meaningful in both
  
  -- directions
  -- Message Waiting Callback
  ssMWICallbackSupported         NULL OPTIONAL, -- meaningful in backward
  
  -- direction
  -- meaningful both in
  -- forward & backward
  -- direction during call
  -- establishment
  -- Call Park
  ssCPCallParkSupported          NULL OPTIONAL, -- meaningful in both
  
  -- directions
  ...
}

FeatureValues ::= SEQUENCE {
  partyCategory        PartyCategory OPTIONAL,
  ssCIprotectionLevel  SSCIProtectionLevel OPTIONAL,
  -- Supplementary Service Call Intrusion Protection level
  -- meaningful both in forward and backward direction; inclusion
  -- indicates support of SS-CI as an unwanted endpoint (forward 
  -- direction) or as a Terminating  Endpoint (backward direction),
  -- as well as the applicable protection level.
  ...
}

PartyCategory ::= ENUMERATED {unknown, extension, attendant, emergExt, ...
                              }

SSCIProtectionLevel ::= INTEGER(0..3)

FeatureControl ::= SEQUENCE {
  ssCHDoNotHold               NULL OPTIONAL, -- meaningful in both directions
  
  -- Sending endpoint shall not be held
  ssCTDoNotTransfer           NULL OPTIONAL, -- meaningful in both directions
  
  -- sending endpoint shall not be transferred
  ssMWICallbackCall           NULL OPTIONAL, -- meaningful only in SETUP 
  
  -- indicating a callback call
  ssCISilentMonitorPermitted  NULL OPTIONAL, -- unwanted endpoint
  
  -- allows for 
  -- silent monitoring
  -- meaningful in forward and backward direction
  ...
}

END -- of Common-Information-Operations

-- Generated by Asnp, the ASN.1 pretty-printer of France Telecom R&D

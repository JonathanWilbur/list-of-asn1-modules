HDISPATCH (V.140:01/2005)


-- Module HDISPATCH (V.140:01/2005)
-- See also ITU-T V.140 (01/2005)
-- See also the index of all ASN.1 assignments needed in this document

HDISPATCH DEFINITIONS AUTOMATIC TAGS ::=
BEGIN

-- Export all symbols
-- ===================================================================================
-- Top level PDUs
-- ===================================================================================
HDispatchPDU ::= CHOICE {
  nonStandard            NonStandardMessage,
  roleAndCapability      RoleAndCapabilityMessage,
  modeSelect             Mode,
  youChoose              NULL,
  modeSelectAcknowledge  NULL,
  terminate              TerminateMessage,
  ...
}

RoleAndCapabilityMessage ::= SEQUENCE {
  role
    CHOICE {originate  NULL,
            unknown    NULL,
            answer     NULL,
            ...},
  arbitrationField  INTEGER(0..4294967295), -- 32 bit random #
  capabilitySet     SEQUENCE SIZE (1..65535) OF Capability,
  ...
}

Capability ::= CHOICE {
  nonStandard  NonStandardParameter,
  isdn
    CHOICE {isdnCapability                 IsdnCapability,
            multilinkAdditionalConnection  NULL, -- Express this cap alone to force--
            -- association of this channel with
            -- an existing call
            is13871
              SEQUENCE-- "BONDING" protocol-- {withIsdnCapability
                                                 IsdnCapability,
                                               ...},
            h244
              SEQUENCE-- channel aggregation protocol-- {withIsdnCapability
                                                           IsdnCapability,
                                                         ...},
            ...},
  ...
}

IsdnCapability ::= CHOICE {
  g711aLaw       SEQUENCE {...},
  g711uLaw       SEQUENCE {...},
  h320           SEQUENCE {...},
  h324AnnexD     SEQUENCE {...},
  h324Multilink  SEQUENCE {...},
  group4Fax      SEQUENCE {...},
  t120           SEQUENCE {...},
  t140           SEQUENCE {...}, -- text chatting protocol
  v110           SEQUENCE {...},
  v120           SEQUENCE {...},
  rfc1661        SEQUENCE {withH323  BOOLEAN,
                           ...},
  ...
}

Mode ::= CHOICE {
  nonStandard                    NonStandardParameter,
  plainIsdnMode                  IsdnMode,
  h244                           IsdnMode,
  is13871                        IsdnMode, -- BONDING protocol
  multilinkAdditionalConnection
    SEQUENCE {callAssociationNumber  INTEGER(0..4294967295),
              ...},
  ...
}

IsdnMode ::= CHOICE {
  nonStandard    NonStandardParameter,
  g711aLaw       SEQUENCE {...},
  g711uLaw       SEQUENCE {...},
  h320           SEQUENCE {...},
  h324AnnexD     SEQUENCE {...},
  h324Multilink  SEQUENCE {...},
  group4Fax      SEQUENCE {...},
  t120           SEQUENCE {...},
  rfc1661        SEQUENCE {...},
  ...
}

TerminateMessage ::= SEQUENCE {
  cause
    CHOICE {nonStandard          NonStandardParameter,
            timerExpiration      NULL,
            roleCollision        NULL,
            noSuitableModes      NULL,
            invalidModeSelected  NULL,
            protocolViolation    NULL,
            modeNotAvailable     NULL,
            ...},
  ...
}

-- ===================================================================================
-- Non standard Message definitions
-- ===================================================================================
NonStandardMessage ::= SEQUENCE {nonStandardData  NonStandardParameter,
                                 ...
}

NonStandardParameter ::= SEQUENCE {
  nonStandardIdentifier  NonStandardIdentifier,
  data                   OCTET STRING
}

NonStandardIdentifier ::= CHOICE {
  object           OBJECT IDENTIFIER,
  h221NonStandard
    SEQUENCE {t35CountryCode    INTEGER(0..255), -- country, per T.35--
              t35Extension      INTEGER(0..255), -- assigned nationally--
              manufacturerCode  INTEGER(0..65535)}
} -- assigned nationally

END

-- Generated by Asnp, the ASN.1 pretty-printer of France Telecom R&D

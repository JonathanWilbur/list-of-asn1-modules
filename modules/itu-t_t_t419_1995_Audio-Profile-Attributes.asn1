Audio-Profile-Attributes (T.419:08/1995)


-- Module Audio-Profile-Attributes (T.419:08/1995)
-- See also ITU-T T.419 (08/1995)
-- See also the index of all ASN.1 assignments needed in this document

Audio-Profile-Attributes {2 8 1 9 4} DEFINITIONS ::=
BEGIN

EXPORTS
  Audio-Presentation-Feature, Audio-Coding-Attribute, Audio-Content-Defaults;

IMPORTS
  Audio-Attributes
    FROM Audio-Presentation-Attributes {2 8 1 9 2}; --  see 11.3

Audio-Presentation-Feature ::= NULL

--  no audio non-basic features are defined in this
--  Recommendation | International Standard
Audio-Coding-Attribute ::= NULL

--  no audio non-basic coding attributes are defined in this
--  Recommendation | International Standard
Audio-Content-Defaults ::=
  Audio-Attributes

END

-- Generated by Asnp, the ASN.1 pretty-printer of France Telecom R&D

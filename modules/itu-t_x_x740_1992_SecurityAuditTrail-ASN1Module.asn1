SecurityAuditTrail-ASN1Module (:)


-- Module SecurityAuditTrail-ASN1Module (:)
-- See also ITU-T X.740 (09/1992)
-- See also the index of all ASN.1 assignments needed in this document

SecurityAuditTrail-ASN1Module {joint-iso-itu-t ms(9) function(2) part8(8)
  asn1Module(2) 2} DEFINITIONS ::=
BEGIN

IMPORTS
  AdditionalText, AdditionalInformation, CorrelatedNotifications,
    NotificationIdentifier
    FROM Attribute-ASN1Module {joint-iso-itu-t ms(9) smi(3) part2(2)
      asn1Module(2) 1};

SecurityAuditInfo ::= SEQUENCE {
  serviceReportCause       ServiceReportCause OPTIONAL,
  notificationIdentifier   NotificationIdentifier OPTIONAL,
  correlatedNotifications  [1] IMPLICIT CorrelatedNotifications OPTIONAL,
  additionalText           AdditionalText OPTIONAL,
  additionalInformation    [2] IMPLICIT AdditionalInformation OPTIONAL
}

ServiceReportCause ::= OBJECT IDENTIFIER

END

-- Generated by Asnp, the ASN.1 pretty-printer of France Telecom R&D

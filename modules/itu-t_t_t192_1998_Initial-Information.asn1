Initial-Information (T.192:06/1998)


-- Module Initial-Information (T.192:06/1998)
-- See also ITU-T T.192 (06/1998)
-- See also the index of all ASN.1 assignments needed in this document

Initial-Information DEFINITIONS IMPLICIT TAGS ::=
BEGIN

IMPORTS
  Document-Reference
    FROM Document-Profile-Descriptor {2 8 1 5 6
      } -- see ITU-T Rec. T.415 | ISO/IEC 8613-5
  DOR
    FROM DOR-definition {joint-iso-itu-t(2) remote-operations(4)
      reference-definition(0)} -- see ISO/IEC 10031-2
  -- Note: DistinguishedName, formerly imported from X.501 InformationFramework,
  --       is imported from X.711 CMIP.
  DistinguishedName
    FROM CMIP-1 {joint-iso-itu-t ms(9) cmip(1) modules(0) protocol(3)};

InitialInformation ::= SEQUENCE {
  complexServiceId   [0]  OCTET STRING,
  staticInformation  [1]  StaticInformation
}

StaticInformation ::= SEQUENCE {
  userIds         [0]  UserIds,
  docIds          [1]  DocIds,
  non-ODA-format  [2]  Non-ODA-format,
  moderatorId     [3]  ModeratorId
}

UserIds ::= SEQUENCE OF UserId

UserId ::= Name

Name ::= CHOICE {formal    [0]  DistinguishedName,
                 informal  [1]  OCTET STRING
}

DocIds ::= SEQUENCE OF DocId

DocId ::= SEQUENCE {document  [0]  DocumentId,
                    site      [1]  SiteId
}

DocumentId ::= CHOICE {
  oda        [0]  Document-Reference,
  doam       [1]  DOR,
  directory  [2]  DistinguishedName,
  object     [3]  OBJECT IDENTIFIER,
  informal   [4]  OCTET STRING
}

SiteId ::= Name

Non-ODA-format ::= OCTET STRING

-- An alternative representation may be used in the future.
ModeratorId ::=
  UserId

END

-- Generated by Asnp, the ASN.1 pretty-printer of France Telecom R&D

M3611-ASN1Module (M.3611:04/1997)


-- Module M3611-ASN1Module (M.3611:04/1997)
-- See also ITU-T M.3611 (04/1997)
-- See also the index of all ASN.1 assignments needed in this document

M3611-ASN1Module {itu-t(0) recommendation(0) m(13) m3611(3611)
  informationModel(0) asn1Modules(2) m3611-ASN1Module(0)} DEFINITIONS IMPLICIT
TAGS ::=
BEGIN

--EXPORTS everything
IMPORTS
  Timespec, TestInvocationId
    FROM Test-ASN1Module {joint-iso-itu-t ms(9) function(2) part12(12)
      asn1Module(2) 0}
  ObjectInstance
    FROM CMIP-1 {joint-iso-itu-t ms(9) cmip(1) modules(0) protocol(3)};

-- Object identifiers
m3611InformationModel OBJECT IDENTIFIER ::=
  {itu-t(0) recommendation(0) m(13) m3611(3611) informationModel(0)}

m3611ObjectClass OBJECT IDENTIFIER ::=
  {m3611InformationModel managedObjectClass(3)}

m3611Package OBJECT IDENTIFIER ::= {m3611InformationModel package(4)}

m3611Parameter OBJECT IDENTIFIER ::= {m3611InformationModel parameter(5)}

m3611NameBinding OBJECT IDENTIFIER ::= {m3611InformationModel nameBinding(6)}

m3611Attribute OBJECT IDENTIFIER ::= {m3611InformationModel attribute(7)}

-- default value definitions
all1sIn16octets LoopbackLocationID ::=
  'FFFFFFFFFFFFFFFFFFFFFFFFFFFFFFFF'H

pointNotDefined AccessPoint ::= undefined:NULL

noInvctn AssignedTestInvctn ::= noTestInvctn:NULL

nullMsrmntTime MeasurementTime ::=
  {days 0, hours 0, minutes 0, seconds 0, milliseconds 0}

-- attribute types
LoopbackLocationID ::= OCTET STRING

ATMTestResults ::= SEQUENCE {
  totalCellNumber                INTEGER,
  totalCellBlockNumber           [0]  INTEGER OPTIONAL,
  cellErrorRatio                 [1]  REAL OPTIONAL,
  cellLossRatio                  [2]  REAL OPTIONAL,
  severelyErroredCellBlockRatio  [3]  REAL OPTIONAL,
  cellMisinsertionRatio          [4]  REAL OPTIONAL,
  cellTransferDelay              [5]  Timespec OPTIONAL,
  cellDelayVariation             [6]  Timespec OPTIONAL
}

ConnectivityOAMAccessID ::= INTEGER

AccessPoint ::= CHOICE {
  defined
    [0]  SEQUENCE {objectinstance   ObjectInstance,
                   signelDirection  SignalDirection},
  undefined  [1]  NULL
}

SignalDirection ::= ENUMERATED {
  in(0), -- insertion before and extraction after the cross connection
  out(1)} -- insertion after and extraction from the cross connection

AssignedTestInvctn ::= CHOICE {
  noTestInvctn  NULL,
  assignedTest  TestInvocationId
}

MeasurementTime ::= SEQUENCE {
  days          [0]  INTEGER,
  hours         [1]  INTEGER, -- 0 to 23
  minutes       [2]  INTEGER, -- 0 to 59
  seconds       [3]  INTEGER, -- 0 to 59
  milliseconds  [4]  INTEGER -- 0 to 999
}

END

-- Generated by Asnp, the ASN.1 pretty-printer of France Telecom R&D

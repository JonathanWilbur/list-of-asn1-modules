ASN1CMANTypeModule (Q.824.5:10/1997)


-- Module ASN1CMANTypeModule (Q.824.5:10/1997)
-- See also ITU-T Q.824.5 (1997) Cor. 1 (02/2000)
-- See also the index of all ASN.1 assignments needed in this document

ASN1CMANTypeModule {itu-t(0) recommendation(0) q(17) ca(824) dot(127)
  v5interface(5) informationModel(0) asn1Module(2) cAV5ANModule(1)} DEFINITIONS
IMPLICIT TAGS ::=
BEGIN

-- EXPORTS everything
IMPORTS
  -- Recommendation X.711 
  ObjectInstance
    FROM CMIP-1 {joint-iso-ccitt ms(9) cmip(1) modules(0) protocol(3)};

informationModel OBJECT IDENTIFIER ::=
  {itu-t(0) recommendation(0) q(17) ca(824) dot(127) v5interface(5)
   informationModel(0)}

standardSpecificExtension OBJECT IDENTIFIER ::=
  {informationModel standardSpecificExtension(0)}

managedObjectClass OBJECT IDENTIFIER ::=
  {informationModel managedObjectClass(3)}

package OBJECT IDENTIFIER ::= {informationModel package(4)}

nameBinding OBJECT IDENTIFIER ::= {informationModel nameBinding(6)}

attribute OBJECT IDENTIFIER ::= {informationModel attribute(7)}

action OBJECT IDENTIFIER ::= {informationModel action(9)}

notification OBJECT IDENTIFIER ::= {informationModel notification(10)}

defaultSpecialFeatures SpecialFeatures ::= {}

AccessDigitalSection ::= BOOLEAN

BearerChannelType ::= ENUMERATED {non-PL-channel(0), pL-channel(1), ...
                                  }

GradingEnabled ::= BOOLEAN

Pointer ::= ObjectInstance

SpecialFeature ::= ENUMERATED {
  directDiallingIn(0), publicTelephone(1), privateMeter(2),
  specialLoopResistance(3), securityLine(4), other(5), ...
  }

SpecialFeatures ::= SET OF SpecialFeature

END -- of ASN1CMANTypeModule

-- Generated by Asnp, the ASN.1 pretty-printer of France Telecom R&D

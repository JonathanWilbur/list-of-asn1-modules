Example2-EDM


-- Generated by Ecnp, the pretty-printer of France Telecom R&amp;D

Example2-EDM {joint-iso-itu-t(2) asn1(1) ecn(4) examples(5) edm-module2(6)}
ENCODING-DEFINITIONS ::=
BEGIN

EXPORTS Example2Encodings;

IMPORTS
  #NormallySmallValues, #SparseEvenlyDistributedValue,
    #SparseUnevenlyDistributedValueSet, #ConditionalPresenceOnValueSet,
    #ConditionalPresenceOnExternalCondition, #EnclosingStructureForList,
    #EqualLengthLists, #EnclosingStructureForChoice, #Version1Message
    FROM Example2-ASN1-Module {joint-iso-itu-t(2) asn1(1) ecn(4) examples(5)
      asn1-module2(5)};

Example2Encodings #ENCODINGS ::= {
  normallySmallValuesEncoding |
   -- etc.
   extensibleMessageEncoding}

-- etc.
END

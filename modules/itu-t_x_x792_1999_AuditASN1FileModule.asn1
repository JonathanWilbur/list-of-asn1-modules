AuditASN1FileModule (X.792:03/1999)


-- Module AuditASN1FileModule (X.792:03/1999)
-- See also ITU-T X.792 (03/1999)
-- See also the index of all ASN.1 assignments needed in this document

AuditASN1FileModule {itu-t recommendation x(24) configAud(792)
  informationModel(0) fileDefinition(3)} DEFINITIONS IMPLICIT TAGS ::=
BEGIN

-- EXPORT Everything
IMPORTS
  ObjectClass, ObjectInstance, Attribute
    FROM CMIP-1 {joint-iso-itu-t ms(9) cmip(1) modules(0) protocol(3)};

AuditFile ::=
  SET OF
    SEQUENCE {managedObjectClass     ObjectClass OPTIONAL,
              managedObjectInstance  ObjectInstance,
              attributeList          SET OF Attribute}

END -- of AuditASN1FileModule 

-- Generated by Asnp, the ASN.1 pretty-printer of France Telecom R&D

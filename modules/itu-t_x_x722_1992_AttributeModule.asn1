AttributeModule (X.722:01/1992)


-- Module AttributeModule (X.722:01/1992)
-- See also ITU-T X.722 (01/1992)
-- See also the index of all ASN.1 assignments needed in this document

AttributeModule {joint-iso-itu-t ms(9) smi(3) part4(4) asn1Module(2)
  attributes(0)} DEFINITIONS ::=
BEGIN

ObjectName ::= GraphicString

QOSErrorCause ::= INTEGER {
  responseTimeExcessive(0), queueSizeExceeded(1), bandwidthReduced(2),
  retransmissionRateExcessive(3)}

QOSErrorCounter ::= INTEGER

QOSCounterRange ::= QOSErrorCounter(0..4294967296) -- Range is 32 bits
                                   

END

-- Generated by Asnp, the ASN.1 pretty-printer of France Telecom R&D

IN-Contexts (Q.1218:10/1995)


-- Module IN-Contexts (Q.1218:10/1995)
-- See also ITU-T Q.1218 (10/1995)
-- See also the index of all ASN.1 assignments needed in this document

IN-Contexts {itu-t recommendation q 1218 modules(0) contexts(8)
  selectedContexts(1) version(1)} DEFINITIONS ::=
BEGIN

IMPORTS
  ub-international-isdn-number
    FROM UpperBounds {joint-iso-itu-t ds(5) module(1) upperBounds(10) 3}
  informationFramework
    FROM UsefulDefinitions {joint-iso-itu-t ds(5) module(1)
      usefulDefinitions(0) 3}
  CONTEXT
    FROM InformationFramework {joint-iso-itu-t ds(5) module(1)
      informationFramework(1) 3};

basicServiceContext CONTEXT ::= {
  WITH SYNTAX  BasicService
  ID           id-avc-basicService
}

BasicService ::= INTEGER {
  telephony(1), faxGroup2-3(2), faxGroup4(3), teletexBasicAndMixed(4),
  teletexBasicAndProcessable(5), teletexBasic(6), syntaxBasedVideotex(7),
  internationalVideotex(8), telex(9), messageHandlingSystems(10),
  osiApplication(11), audioVisual(12)}

lineIdentityContext CONTEXT ::= {
  WITH SYNTAX  IsdnAddress
  ID           id-avc-lineIdentity
}

AddressString{INTEGER:ub-max-value} ::= NumericString(SIZE (1..ub-max-value))

IsdnAddress ::= AddressString{ub-international-isdn-number}

id-avc-basicService OBJECT IDENTIFIER ::= {id-avc 30}

id-avc-lineIdentity OBJECT IDENTIFIER ::= {id-avc 31}

id-avc OBJECT IDENTIFIER ::= {itu-t recommendation q 1218 contexts(8)}

END

-- Generated by Asnp, the ASN.1 pretty-printer of France Telecom R&D

V151SPRT-CAPABILITY (V.151:05/2006)


-- Module V151SPRT-CAPABILITY (V.151:05/2006)
-- See also ITU-T V.151 (2006) Amend. 1 (08/2007)
-- See also the index of all ASN.1 assignments needed in this document

V151SPRT-CAPABILITY DEFINITIONS AUTOMATIC TAGS ::=
BEGIN

IMPORTS NonStandardParameter
          FROM MULTIMEDIA-SYSTEM-CONTROL;

V150MoIPCapability ::= SEQUENCE {
  nonStandard     SEQUENCE OF NonStandardParameter OPTIONAL,
  sprtParameters
    SEQUENCE {maxPayloadSizeChannel0  INTEGER(140..256) OPTIONAL, -- Default 140--
              maxPayloadSizeChannel1  INTEGER(132..256) OPTIONAL, -- Default 132--
              maxWindowSizeChannel1   INTEGER(32..96) OPTIONAL, -- Default 32--
              maxPayloadSizeChannel2  INTEGER(132..256) OPTIONAL, -- Default 132--
              maxWindowSizeChannel2   INTEGER(8..32) OPTIONAL, -- Default 8,--
              maxPayloadSizeChannel3  INTEGER(140..256) OPTIONAL, -- Default 140--
              ...} OPTIONAL,
  ...
}

END

-- Generated by Asnp, the ASN.1 pretty-printer of France Telecom R&D

MEDIA-OVER-H2250 (H.460.26:06/2012)


-- Module MEDIA-OVER-H2250 (H.460.26:06/2012)
-- See also ITU-T H.460.26 (06/2012)
-- See also the index of all ASN.1 assignments needed in this document

MEDIA-OVER-H2250 {itu-t(0) recommendation(0) h(8) 460 26 version(0) 1
  media-over-h2250(0)} DEFINITIONS AUTOMATIC TAGS ::=
BEGIN

FrameData ::= CHOICE {
  rtp   OCTET STRING(SIZE (12..1500)),
  rtcp  OCTET STRING(SIZE (1..1500))
}

UDPFrame ::= SEQUENCE {
  sessionId  INTEGER(0..255),
  dataFrame  BOOLEAN,
  frame      SEQUENCE OF FrameData
}

END

-- Generated by Asnp, the ASN.1 pretty-printer of France Telecom R&D

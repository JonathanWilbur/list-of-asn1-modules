IN-CS3-SCF-CUSF-Classes (Q.1238.7:06/2000)


-- Module IN-CS3-SCF-CUSF-Classes (Q.1238.7:06/2000)
-- See also ITU-T Q.1238.7 (06/2000)
-- See also the index of all ASN.1 assignments needed in this document

-- 13.2	CLASS DEFINITION
-- This clause specifies the class definitions and the class type definitions used
-- in CUSF-SCF relationship.
IN-CS3-SCF-CUSF-Classes {itu-t recommendation q 1238 modules(1)
  in-cs3-scf-cusf-classes(25) version1(0)} DEFINITIONS ::=
BEGIN

IMPORTS
  common-classes, ssf-scf-classes
    FROM IN-CS3-object-identifiers {itu-t recommendation q 1238 modules(1)
      in-cs3-object-identifiers(0) version1(0)}
  COMMON-BOUNDS
    FROM IN-CS3-common-classes {itu-t recommendation q 1238 modules(1)
      in-cs3-common-classes(5) version1(0)}
  SCF-SSF-BOUNDS
    FROM IN-CS3-SSF-SCF-Classes {itu-t recommendation q 1238 modules(1)
      in-cs3-ssf-scf-classes(7) version1(0)};

SCF-CUSF-BOUNDS ::= CLASS {
  &minAssReleaseInfoLen    INTEGER OPTIONAL,
  &maxAssReleaseInfoLen    INTEGER OPTIONAL,
  &minCompReceivedInfoLen  INTEGER OPTIONAL,
  &maxCompReceivedInfoLen  INTEGER OPTIONAL,
  &numOfBCUSMEvents        INTEGER OPTIONAL
}
WITH SYNTAX {
  [MINIMUM-FOR-ASS-RELEASE-INFO-LENGTH &minAssReleaseInfoLen]
  [MAXIMUM-FOR-ASS-RELEASE-INFO-LENGTH &maxAssReleaseInfoLen]
  [MINIMUM-FOR-COMP-RECEIVED-INFO-LENGTH &minCompReceivedInfoLen]
  [MAXIMUM-FOR-COMP-RECEIVED-INFO-LENGTH &maxCompReceivedInfoLen]
  [NUM-OF-BCUSM-EVENTS &numOfBCUSMEvents]
}

-- The following definitions of the parameter bounds are an example.
-- Appropriate values will be defined as network specific.
sCFCUSFBoundSet SCF-CUSF-BOUNDS ::= {
  MINIMUM-FOR-ASS-RELEASE-INFO-LENGTH    5
  MAXIMUM-FOR-ASS-RELEASE-INFO-LENGTH    10
  MINIMUM-FOR-COMP-RECEIVED-INFO-LENGTH  5
  MAXIMUM-FOR-COMP-RECEIVED-INFO-LENGTH  10
  NUM-OF-BCUSM-EVENTS                    2
}

sCFSSFBoundSetforCUSF SCF-SSF-BOUNDS ::= {
  MAXIMUM-FOR-BEARER-CAPABILITY         5 -- example value
  MINIMUM-FOR-CALLED-PARTY-NUMBER       2 -- example value
  MAXIMUM-FOR-CALLED-PARTY-NUMBER       10 -- example value
  MINIMUM-FOR-CALLING-PARTY-NUMBER      2 -- example value
  MAXIMUM-FOR-CALLING-PARTY-NUMBER      10 -- example value
  MINIMUM-FOR-CALLING-PARTY-SUBADDRESS  2 -- example value
  MAXIMUM-FOR-CALLING-PARTY-SUBADDRESS  5 -- example value
  MINIMUM-FOR-CAUSE                     2 -- example value
  MAXIMUM-FOR-CAUSE                     10 -- example value
  -- MINIMUM-FOR-FORWARD-GVNS		1 ??? example value
  -- MAXIMUM-FOR-FORWARD-GVNS		5 ??? example value
  -- MINIMUM-FOR-GENERIC-NAME		1 ??? example value
  -- MAXIMUM-FOR-GENERIC-NAME		5 ??? example value
  MINIMUM-FOR-GENERIC-NUMBER            3 -- example value
  MAXIMUM-FOR-GENERIC-NUMBER            10 -- example value
  -- MINIMUM-FOR-IP-AVAILABLE		1 ??? example value
  -- MAXIMUM-FOR-IP-AVAILABLE		5 ??? example value
  -- MINIMUM-FOR-IP-SSP-CAPABILITIES	1 ??? example value
  -- MAXIMUM-FOR-IP-SSP-CAPABILITIES	5 ??? example value
  -- MINIMUM-FOR-ISDN-ACCESS-RELATED-INFO	1 ??? example value
  -- MAXIMUM-FOR-ISDN-ACCESS-RELATED-INFO	5 ??? example value
  MINIMUM-FOR-LOCATION-NUMBER           2 -- example value
  MAXIMUM-FOR-LOCATION-NUMBER           10 -- example value
  -- MINIMUM-FOR-MID-CALL-CONTROL-INFO	1 ??? example value
  -- MAXIMUM-FOR-MID-CALL-CONTROL-INFO	5 ??? example value
  -- MINIMUM-FOR-ORIGINAL-CALLED-PARTY-ID	1 ??? example value
  -- MAXIMUM-FOR-ORIGINAL-CALLED-PARTY-ID	5 ??? example value
  -- MINIMUM-FOR-REASON			1 ??? example value
  -- MAXIMUM-FOR-REASON			5 ??? example value
  -- MINIMUM-FOR-REDIRECTING-ID		1 ??? example value
  -- MAXIMUM-FOR-REDIRECTING-ID		5 ??? example value
  MINIMUM-FOR-REQUESTED-UTSI-NUM        1 -- example value
  MAXIMUM-FOR-REQUESTED-UTSI-NUM        5 -- example value
  -- MINIMUM-FOR-ROUTE-LIST		1 ??? example value
  -- MAXIMUM-FOR-ROUTE-LIST		5 ??? example value
  -- MINIMUM-FOR-ROUTING-NUMBER		1 ??? example value
  -- MAXIMUM-FOR-ROUTING-NUMBER		5 ??? example value
  -- MINIMUM-FOR-SCF-ID			1 ??? example value
  -- MAXIMUM-FOR-SCF-ID			5 ??? example value
  -- MINIMUM-FOR-SCI-BILLING-CHARGING	1 ??? example value
  -- MAXIMUM-FOR-SCI-BILLING-CHARGING	1 ??? example value
  -- MINIMUM-FOR-SDSS-INFORMATION		1 ??? example value
  -- MAXIMUM-FOR-SDSS-INFORMATION		1 ??? example value
  -- MINIMUM-FOR-SII			1 ??? example value
  -- MAXIMUM-FOR-SII			5 ??? example value
  -- MINIMUM-FOR-SF-BILLING-CHARGING	1 ??? example value
  -- MAXIMUM-FOR-SF-BILLING-CHARGING	5 ??? example value
  MINIMUM-FOR-USI-INFORMATION           1 -- example value
  MAXIMUM-FOR-USI-INFORMATION           20 -- example value
  MINIMUM-FOR-USI-SERVICE-INDICATOR     1 -- example value
  MAXIMUM-FOR-USI-SERVICE-INDICATOR     10 -- example value
  -- NUM-OF-BCSM-EVENT			13 ??? example value
  -- NUM-OF-BCUSM-EVENT			13 ??? example value
  -- NUM-OF-CSAS				13 ??? example value
  -- NUM-OF-CSS				13 ??? example value
  NUM-OF-GENERIC-NUMBERS                5 -- example value


-- NUM-OF-INPROFILE			2 ??? example value
-- NUM-OF-SEVERAL-TRIGGER		13 ??? example value
-- NUM-OF-IN-SERVICE-COMPATIBILITY-ID	13 ??? example value
-- NUM-OF-LEGS				13 ??? example value
-- MAXIMUM-FOR-CALL-REFERENCE		5 ??? example value
-- NUM-OF-ADDRESSES			13 ??? example value
}

commonBoundSetforCUSF COMMON-BOUNDS ::= {NUM-OF-EXTENSIONS  1
}

END

-- Generated by Asnp, the ASN.1 pretty-printer of France Telecom R&D

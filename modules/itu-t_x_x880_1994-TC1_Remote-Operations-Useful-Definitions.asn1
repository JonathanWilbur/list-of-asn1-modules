Remote-Operations-Useful-Definitions (Rec. X.880:07/1994)


-- Module Remote-Operations-Useful-Definitions (X.880:07/1994)-- See also ITU-T X.880 (1994) Technical Cor. 1 (07/1995)-- See also the index of all ASN.1 assignments needed in this Recommendation

Remote-Operations-Useful-Definitions {joint-iso-itu-t remote-operations(4)
  useful-definitions(7) version1(0)} DEFINITIONS IMPLICIT TAGS ::=
BEGIN

-- exports everything
IMPORTS
  OPERATION, ERROR, OPERATION-PACKAGE, Code
    FROM Remote-Operations-Information-Objects {joint-iso-itu-t
      remote-operations(4) informationObjects(5) version1(0)}
  InvokeId, ROS{}
    FROM Remote-Operations-Generic-ROS-PDUs {joint-iso-itu-t
      remote-operations(4) generic-ROS-PDUs(6) version1(0)};

emptyBind OPERATION ::= {ERRORS       {refuse}
                         SYNCHRONOUS  TRUE
}

emptyUnbind OPERATION ::= {SYNCHRONOUS  TRUE
}

refuse ERROR ::= {CODE  local:-1
}

no-op OPERATION ::= {ALWAYS RESPONDS  FALSE
                     CODE             local:-1
}

Forward{OPERATION:OperationSet} OPERATION ::=
  {OperationSet | OperationSet.&amp;Linked.&amp;Linked |
   OperationSet.&amp;Linked.&amp;Linked.&amp;Linked.&amp;Linked}

Reverse{OPERATION:OperationSet} OPERATION ::=
  {Forward{{OperationSet.&amp;Linked}}}

ConsumerPerforms{OPERATION-PACKAGE:package} OPERATION ::=
  {Forward{{package.&amp;Consumer}} | Forward{{package.&amp;Both}} |
   Reverse{{package.&amp;Supplier}} | Reverse{{package.&amp;Both}}}

SupplierPerforms{OPERATION-PACKAGE:package} OPERATION ::=
  {Forward{{package.&amp;Supplier}} | Forward{{package.&amp;Both}} |
   Reverse{{package.&amp;Consumer}} | Reverse{{package.&amp;Both}}}

AllOperations{OPERATION-PACKAGE:package} OPERATION ::=
  {ConsumerPerforms{package} | SupplierPerforms{package}}

-- continued on the next page
recode{OPERATION:operation, Code:code} OPERATION ::= {
  ARGUMENT         operation.&amp;ArgumentType
  OPTIONAL         operation.&amp;argumentTypeOptional
  RESULT           operation.&amp;ResultType
  OPTIONAL         operation.&amp;resultTypeOptional
  RETURN RESULT    operation.&amp;returnResult
  ERRORS           {operation.&amp;Errors}
  LINKED           {operation.&amp;Linked}
  SYNCHRONOUS      operation.&amp;synchronous
  ALWAYS RESPONDS  operation.&amp;alwaysReturns
  INVOKE PRIORITY  {operation.&amp;InvokePriority}
  RESULT-PRIORITY  {operation.&amp;ResultPriority}
  CODE             code
}

switch{OPERATION-PACKAGE:package, OBJECT IDENTIFIER:id} OPERATION-PACKAGE ::= 
{
  OPERATIONS        {package.&amp;Both}
  CONSUMER INVOKES  {package.&amp;Consumer}
  SUPPLIER INVOKES  {package.&amp;Supplier}
  ID                id
}

combine{OPERATION-PACKAGE:ConsumerConsumes, OPERATION-PACKAGE:ConsumerSupplies,
        OPERATION-PACKAGE:base} OPERATION-PACKAGE ::= {
  OPERATIONS        {ConsumerConsumes.&amp;Both | ConsumerSupplies.&amp;Both}
  CONSUMER INVOKES
    {ConsumerConsumes.&amp;Consumer | ConsumerSupplies.&amp;Supplier}
  SUPPLIER INVOKES
    {ConsumerConsumes.&amp;Supplier | ConsumerSupplies.&amp;Consumer}
  ID                base.&amp;id
}

ROS-SingleAS{InvokeId:InvokeIdSet, OPERATION-PACKAGE:package} ::=
  ROS{{InvokeIdSet}, {AllOperations  {package}}, {AllOperations  {package}}}

ROS-ConsumerAS{InvokeId:InvokeIdSet, OPERATION-PACKAGE:package} ::=
  ROS
    {{InvokeIdSet}, {ConsumerPerforms  {package}},
    {SupplierPerforms  {package}}}

ROS-SupplierAS{InvokeId:InvokeIdSet, OPERATION-PACKAGE:package} ::=
  ROS
    {{InvokeIdSet}, {SupplierPerforms  {package}},
    {ConsumerPerforms  {package}}}

END -- end of useful definitions.

-- Generated by Asnp, the ASN.1 pretty-printer of France Telecom R&amp;D

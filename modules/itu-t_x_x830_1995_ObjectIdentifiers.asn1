ObjectIdentifiers (X.830:04/1995)


-- Module ObjectIdentifiers (X.830:04/1995)
-- See also ITU-T X.830 (04/1995)
-- See also the index of all ASN.1 assignments needed in this document

ObjectIdentifiers {joint-iso-itu-t genericULS(20) modules(1)
  objectIdentifiers(0)} DEFINITIONS AUTOMATIC TAGS ::=
BEGIN

-- EXPORTS All 
genericULS OBJECT IDENTIFIER ::=
  {joint-iso-itu-t genericULS(20)}

-- Categories of information object 
modules OBJECT IDENTIFIER ::=
  {genericULS 1}

generalTransferSyntax OBJECT IDENTIFIER ::= {genericULS 2}

specificTransferSyntax OBJECT IDENTIFIER ::= {genericULS 3}

securityExchanges OBJECT IDENTIFIER ::= {genericULS 4}

securityTransformations OBJECT IDENTIFIER ::= {genericULS 5}

-- ASN.1 modules 
objectIdentifiers OBJECT IDENTIFIER ::= {modules 0}

notation OBJECT IDENTIFIER ::= {modules 1}

gulsSecurityExchanges OBJECT IDENTIFIER ::= {modules 2}

gulsSecurityTransformations OBJECT IDENTIFIER ::= {modules 3}

dirProtectionMappings OBJECT IDENTIFIER ::= {modules 4}

gulsProtectionMappings OBJECT IDENTIFIER ::= {modules 5}

seseAPDUs OBJECT IDENTIFIER ::= {modules 6}

genericProtectingTransferSyntax OBJECT IDENTIFIER ::= {modules 7}

END

-- Generated by Asnp, the ASN.1 pretty-printer of France Telecom R&D

<!-- content of stack:

-->

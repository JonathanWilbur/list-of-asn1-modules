M2 (X.683:07/2002)


-- Module M2 (X.683:07/2002)
-- See also ITU-T X.683 (07/2002)
-- See also the index of all ASN.1 assignments needed in this document

M2 DEFINITIONS EXPLICIT TAGS ::=
BEGIN

IMPORTS T1
          FROM M1;

T3 ::= T2{T1}

T2{X} ::= SEQUENCE {a  INTEGER,
                    b  X
}

END

-- Generated by Asnp, the ASN.1 pretty-printer of France Telecom R&D

Example3-ASN1-Module (X.692:11/2008)


-- Module Example3-ASN1-Module (X.692:11/2008)
-- See also standard
-- See also the index of all ASN.1 assignments needed in this document

Example3-ASN1-Module {joint-iso-itu-t(2) asn1(1) ecn(4) examples(5)
  asn1-module3(9)} DEFINITIONS AUTOMATIC TAGS ::=
BEGIN

Sequence1 ::= SEQUENCE {
  component1  BOOLEAN OPTIONAL,
  component2  INTEGER OPTIONAL,
  component3  VisibleString
}

sequence1 Sequence1 ::= {component2 1, component3 "component3"}

Sequence2 ::= SEQUENCE {
  component1  BOOLEAN OPTIONAL,
  component2  INTEGER,
  component3  VisibleString OPTIONAL
}

sequence2 Sequence2 ::= {component1 TRUE, component2 10}

Octet3 ::= OCTET STRING(CONTAINING Sequence3)

octet3 Octet3 ::=
  CONTAINING{component1 '01010101'B, component2 '01010101'H, component3
             "component3"}

Sequence3 ::= SEQUENCE {
  component1  [0]  BIT STRING(SIZE (0..2047)) OPTIONAL,
  component2  [1]  OCTET STRING(SIZE (0..2047)) OPTIONAL,
  component3  [2]  VisibleString(SIZE (0..2047)) OPTIONAL
}

SequenceOfIntegers ::= SEQUENCE (SIZE (0..63)) OF INTEGER(0..1023)

sequenceOfIntegers SequenceOfIntegers ::= {0, 1023}

END

-- Generated by Asnp, the ASN.1 pretty-printer of France Telecom R&D

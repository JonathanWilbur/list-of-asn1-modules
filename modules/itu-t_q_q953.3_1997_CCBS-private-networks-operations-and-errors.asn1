CCBS-private-networks-operations-and-errors (Q.953.3:06/1997)


-- Module CCBS-private-networks-operations-and-errors (Q.953.3:06/1997)
-- See also ITU-T Q.953.3 (06/1997)
-- See also the index of all ASN.1 assignments needed in this document

CCBS-private-networks-operations-and-errors {itu-t recommendation q 953 
  ccbs(3) private-networks-operations-and-errors(2)} DEFINITIONS EXPLICIT TAGS
::=
BEGIN

EXPORTS
  cCBS-T-Request, cCBS-T-Call, cCBS-T-Suspend, cCBS-T-Resume,
    cCBS-T-RemoteUserFree, cCBS-T-Available, shortTermDenial, longTermDenial;

IMPORTS
  OPERATION, ERROR
    FROM Remote-Operations-Information-Objects {joint-iso-itu-t
      remote-operations(4) informationObjects(5) version1(0)}
  userNotSubscribed
    FROM General-Error-List {itu-t recommendation q 950 general-error-list(1)}
  Address
    FROM Addressing-Data-Elements {itu-t recommendation q 932
      addressing-data-elements(7)}
  Q931InformationElement
    FROM Embedded-Q931-Types {itu-t recommendation q 932 embedded-q931-types(5)
      };

cCBS-T-Request OPERATION ::= {
  ARGUMENT
    SEQUENCE {destinationAddress            Address,
              q931InfoElement               Q931InformationElement,
              -- contains HLC, LLC and BC information
              retentionSupported            [1] IMPLICIT BOOLEAN DEFAULT FALSE,
              presentationAllowedIndicator  [2] IMPLICIT BOOLEAN OPTIONAL,
              originatingAddress            Address OPTIONAL}
  RESULT         RetentionSupported -- FALSE default
  RETURN RESULT  FALSE
  ERRORS         {shortTermDenial | userNotSubscribed | longTermDenial}
  CODE           local:83
}

RetentionSupported ::= BOOLEAN

cCBS-T-Call OPERATION ::= {CODE  local:84
}

cCBS-T-Suspend OPERATION ::= {CODE  local:85
}

cCBS-T-Resume OPERATION ::= {CODE  local:86
}

cCBS-T-RemoteUserFree OPERATION ::= {CODE  local:87
}

cCBS-T-Available OPERATION ::= {CODE  local:88
}

shortTermDenial ERROR ::= {CODE  local:59
} --	used at the user A T reference point

longTermDenial ERROR ::= {CODE  local:60
} --	used at the user A T reference point

END -- of CCBS-private-networks-operations-and-errors

-- Generated by Asnp, the ASN.1 pretty-printer of France Telecom R&D

Network-Protocol-Profile-component (Q.932:05/1998)


-- Module Network-Protocol-Profile-component (Q.932:05/1998)
-- See also ITU-T Q.932 (1998) Amend. 1 (06/2000)
-- See also the index of all ASN.1 assignments needed in this document

Network-Protocol-Profile-component {iso(1) standard(0)
  pss1-generic-procedures(11582) network-protocol-profile-component(8)}
DEFINITIONS ::=
BEGIN

EXPORTS NetworkProtocolProfile;

NetworkProtocolProfile ::= [18] IMPLICIT INTEGER {acse(19), dse(32)}(0..254)

END -- of Network-Protocol-Profile-component

-- Generated by Asnp, the ASN.1 pretty-printer of France Telecom R&D

Three-Party-Operations (Q.954.2:10/1995)


-- Module Three-Party-Operations (Q.954.2:10/1995)
-- See also ITU-T Q.954.2 (10/1995)
-- See also the index of all ASN.1 assignments needed in this document

Three-Party-Operations {itu-t(0) recommendation(0) q(17) q954(954) part2(2)
  operations-and-errors(1)} DEFINITIONS EXPLICIT TAGS ::=
BEGIN

EXPORTS begin3PTY, end3PTY;

IMPORTS
  OPERATION
    FROM Remote-Operations-Information-Objects {joint-iso-itu-t
      remote-operations(4) informationObjects(5) version1(0)}
  userNotSubscribed, notAvailable, invalidCallState, resourceUnavailable,
    supplementaryServiceInteractionNotAllowed
    FROM General-Error-List {itu-t recommendation q 950 general-error-list(1)};

begin3PTY OPERATION ::= {
  ERRORS
    {userNotSubscribed | notAvailable | invalidCallState | resourceUnavailable
      | supplementaryServiceInteractionNotAllowed}
  CODE    local:4
}

-- This Recommendation does not provide procedures for the generation of the error "notAvailable"
end3PTY OPERATION ::= {ERRORS  {invalidCallState}
                       CODE    local:5
}

END

-- Generated by Asnp, the ASN.1 pretty-printer of France Telecom R&D

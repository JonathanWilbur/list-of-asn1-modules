MdmpmfASN1Module (X.749:08/1997)


-- Module MdmpmfASN1Module (X.749:08/1997)
-- See also ITU-T X.749 (08/1997)
-- See also the index of all ASN.1 assignments needed in this document

MdmpmfASN1Module {joint-iso-itu-t ms(9) function(2) part19(19) asn1Module(2) 2}
DEFINITIONS ::=
BEGIN

IMPORTS
  ObjectInstance, CMISFilter, ActionArgument, GetArgument, SetArgument
    FROM CMIP-1 {joint-iso-itu-t ms(9) cmip(1) modules(0) protocol(3)}
  SimpleNameType
    FROM Attribute-ASN1Module {joint-iso-itu-t ms(9) smi(3) part2(2)
      asn1Module(2) 1}
  CommonError, OperationResult
    FROM Schedulerev1-ASN1Module {joint-iso-itu-t ms(9) function(2) part15(15)
      modules(2)}
  TimeStamp
    FROM TimeRepresentation {joint-iso-itu-t ms(9) function(2) part20(20)
      asn1Module(2) timeRepresentation(2)};

ApplyOperationToMembershipReply ::= SEQUENCE OF OperationResult

ApplyOperationToMembershipRequest ::= CHOICE {
  set     [0] IMPLICIT SetArgument,
  action  [1] IMPLICIT ActionArgument,
  get     [2] IMPLICIT GetArgument
}

Completeness ::= ENUMERATED {
  completenessUnknown(0), knownComplete(1), knownNotComplete(2)}

DetermineViolationStatusReply ::= ENUMERATED {
  unknown(1), no-violation(2), violation-detected(3), non-member(4)}

DetermineViolationStatusRequest ::= ObjectInstance

InformationString ::= GeneralString

ListMembershipReply ::= SEQUENCE {
  completeness  Completeness,
  membership    Membership
}

Membership ::= SET OF ObjectInstance

MembershipStatus ::= ENUMERATED {unknown(1), member(2), non-member(3)}

Nothing ::= NULL

PolicyViolation ::= SEQUENCE {
  violatorName    ObjectInstance,
  violatedPolicy  ObjectInstance
}

VerifyMembershipStatusReply ::= SEQUENCE {
  objectName        ObjectInstance,
  membershipStatus  MembershipStatus
}

VerifyMembershipStatusRequest ::= ObjectInstance

ViolationStatus ::= ENUMERATED {
  unknown(1), no-violation(2), violation-detected(3)}

END

-- Generated by Asnp, the ASN.1 pretty-printer of France Telecom R&D

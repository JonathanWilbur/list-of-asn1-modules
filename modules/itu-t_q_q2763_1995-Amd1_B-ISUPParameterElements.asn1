B-ISUPParameterElements (Q.2763:12/1999)


-- Module B-ISUPParameterElements (Q.2763:12/1999)
-- See also ITU-T Q.2763 (1999) Amend. 1 (12/2002)
-- See also the index of all ASN.1 assignments needed in this document

B-ISUPParameterElements DEFINITIONS IMPLICIT TAGS ::=
BEGIN

AALParametersField ::= OCTET STRING(SIZE (1..13))

--	coding as AAL parameters info element Q.2931 starting with octet 5
AddressSignal ::= ENUMERATED {
  digit0(0), digit1(1), digit2(2), digit3(3), digit4(4), digit5(5), digit6(6),
  digit7(7), digit8(8), digit9(9), sTsignal(15)}

BinaryCode ::= INTEGER(0..65535) --	maximum value 216 - 1
                      

BroadbandBearerCapabilityField ::= OCTET STRING(SIZE (2..11))

--	coding as Broadband BC info element in Q.2931 starting with octet 5
BroadbandHighLayerInformationField ::= OCTET STRING(SIZE (2..3))

--	coding as Broadband HLC info element in Q.2931 starting with octet 5
BroadbandLowLayerInformationField ::= OCTET STRING(SIZE (2..14))

--	coding as Broadband LLC info element in Q.2931 including the header
CalledAddressSignal ::= ENUMERATED {
  digit0(0), digit1(1), digit2(2), digit3(3), digit4(4), digit5(5), digit6(6),
  digit7(7), digit8(8), digit9(9), code11(11), code12(12), sTsignal(15)
}

CalledPartySubaddressField ::= OCTET STRING(SIZE (1..20))

--	coding as SUB info element in Q.2931 starting with octet 5
CallingAddressSignal ::= ENUMERATED {
  digit0(0), digit1(1), digit2(2), digit3(3), digit4(4), digit5(5), digit6(6),
  digit7(7), digit8(8), digit9(9), code11(11), code12(12)}

CallingPartySubaddressField ::= OCTET STRING(SIZE (1..20))

--	coding as SUB info element in Q.2931 starting with octet 5
CellRateID ::= INTEGER(0..16777215) --	maximum value 224 - 1
                      

ConnectedSubaddressField ::= OCTET STRING(SIZE (1..20))

--	coding as SUB info element in Q.2951 starting with octet 5
ControlID ::= INTEGER(0..4294967295) --	maximum value 232 - 1
                     

MLPPServiceDomain ::= INTEGER(0..16777215) --	maximum value 224 - 1
                             

NarrowbandBearerCapabilityField ::= OCTET STRING(SIZE (2..11))

--	coding as Narrowband BC info element in Q.2931 including the header
NarrowbandHighLayerCompaField ::= OCTET STRING(SIZE (2..3))

--	coding as Narrowband HLC info element in Q.2931 including the header
NarrowbandLowLayerCompaField ::= OCTET STRING(SIZE (2..14))

--	coding as Narrowband LLC info element in Q.2931 including the header
NIdigit ::= INTEGER(0..9)

OAMTrafficDescriptorField ::= OCTET STRING(SIZE (2..10))

--	coding as OAM traffic descriptor IE in Q.2931 starting with octet 5
ProgressIndicatorField ::= OCTET STRING(SIZE (2))

--	coding as PROGRESS info element in Q.2931 including the header
DelayValue ::= INTEGER(0..65535) --	maximum value 216 - 1
                      

RedirectionCounter ::= INTEGER(0..5)

SignallingPointCode ::= INTEGER(0..4095) --	maximum value 212 - 1
                               

UserToUserInformationField ::= OCTET STRING(SIZE (1..128))

--	coding as UUI info element in clause 1/Q.2957 starting with octet 5
VirtualChannelID ::= INTEGER(1..65535) --	maximum value 216 - 1
                            

VirtualPathConnectionID ::= INTEGER(1..65535) --	maximum value 216 - 1
                                   

END

-- Generated by Asnp, the ASN.1 pretty-printer of France Telecom R&D

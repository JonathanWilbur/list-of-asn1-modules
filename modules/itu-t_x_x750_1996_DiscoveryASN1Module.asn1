DiscoveryASN1Module (X.750:10/1996)


-- Module DiscoveryASN1Module (X.750:10/1996)
-- See also ITU-T X.750 (1996) Technical Cor. 1 (02/2000)
-- See also the index of all ASN.1 assignments needed in this document

DiscoveryASN1Module {joint-iso-itu-t(2) ms(9) function(2) part16(16)
  asn1Modules(2) 2} DEFINITIONS IMPLICIT TAGS ::=
BEGIN

-- EXPORTS everything;
IMPORTS
  GdmoObjectClass
    FROM RepertoireASN1Module {joint-iso-itu-t(2) ms(9) function(2) part16(16)
      asn1Modules(2) 0}
  -- this Recommendation | International Standard
  RelativeDistinguishedName, ObjectInstance, Scope
    FROM CMIP-1 {joint-iso-itu-t(2) ms(9) cmip(1) modules(0) protocol(3)}-- ITU-T Rec. X.711 and ISO/IEC 9596-1
  ;

DiscoveryId ::= GraphicString

MITSearch ::= SEQUENCE {
  base            ObjectInstance,
  discoveryScope  Scope,
  classRequest    BOOLEAN DEFAULT FALSE
  -- if true, include class with MITSearchResponse
}

MITSearchResponse ::= SET OF RootedNameTree

NameTree ::= SEQUENCE {
  rdnInfo       RDNInfo,
  subordinates  SET OF NameTree OPTIONAL
}

RDNInfo ::= SEQUENCE {
  rdn      RelativeDistinguishedName,
  moClass  GdmoObjectClass OPTIONAL
}

RootedNameTree ::= SEQUENCE {
  rootObject    ObjectInstance,
  classOfRoot   GdmoObjectClass OPTIONAL,
  subordinates  SET OF NameTree OPTIONAL
}

END

-- Generated by Asnp, the ASN.1 pretty-printer of France Telecom R&D
